TPLINK-SSL-MIB	DEFINITIONS ::= BEGIN
	IMPORTS
		MODULE-IDENTITY, OBJECT-TYPE 
			FROM SNMPv2-SMI   
	    tplinkMgmt
			FROM TPLINK-MIB;
      	
      	tplinkSslMIB MODULE-IDENTITY
			LAST-UPDATED    "201212130930Z"
			ORGANIZATION    "TPLINK"
			CONTACT-INFO    "www.tplink.com"
			DESCRIPTION	    "Private MIB for SSL configuration."
			REVISION        "201212130930Z"
			DESCRIPTION
					"Initial version of this MIB module."
			::= { tplinkMgmt 42 }
			
			tplinkSslMIBObjects OBJECT IDENTIFIER ::= {tplinkSslMIB 1}
        	tplinkSslNotifications OBJECT IDENTIFIER ::= {tplinkSslMIB 2}
      	      
      	    tpHttpsEnable OBJECT-TYPE
	          SYNTAX  INTEGER{
	      		disable(0), 						
	      		enable(1)						
	      		}
	            MAX-ACCESS  read-write
	            STATUS  current
	            DESCRIPTION
	                    "0. disable 
	                     1. enable"
	            ::= { tplinkSslMIBObjects 1 }
			
			tpSslv3Enable OBJECT-TYPE
	          SYNTAX  INTEGER{
	      		disable(0), 						
	      		enable(1)						
	      		}
	            MAX-ACCESS  read-write
	            STATUS  current
	            DESCRIPTION
	                    "0. disable 
	                     1. enable"
	            ::= { tplinkSslMIBObjects 2 }
				
			tpTlsv1Enable OBJECT-TYPE
	          SYNTAX  INTEGER{
	      		disable(0), 						
	      		enable(1)						
	      		}
	            MAX-ACCESS  read-write
	            STATUS  current
	            DESCRIPTION
	                    "0. disable 
	                     1. enable"
	            ::= { tplinkSslMIBObjects 3 }
				
			tpRc4Md5 OBJECT-TYPE
	          SYNTAX  INTEGER{
	      		disable(0), 						
	      		enable(1)						
	      		}
	            MAX-ACCESS  read-write
	            STATUS  current
	            DESCRIPTION
	                    "0. disable 
	                     1. enable"
	            ::= { tplinkSslMIBObjects 4 }
				
			tpRc4Sha OBJECT-TYPE
	          SYNTAX  INTEGER{
	      		disable(0), 						
	      		enable(1)						
	      		}
	            MAX-ACCESS  read-write
	            STATUS  current
	            DESCRIPTION
	                    "0. disable 
	                     1. enable"
	            ::= { tplinkSslMIBObjects 5 }
				
			tpDesCbcSha OBJECT-TYPE
	          SYNTAX  INTEGER{
	      		disable(0), 						
	      		enable(1)						
	      		}
	            MAX-ACCESS  read-write
	            STATUS  current
	            DESCRIPTION
	                    "0. disable 
	                     1. enable"
	            ::= { tplinkSslMIBObjects 6 }
				
			tp3DesEdeCbcSha OBJECT-TYPE
	          SYNTAX  INTEGER{
	      		disable(0), 						
	      		enable(1)						
	      		}
	            MAX-ACCESS  read-write
	            STATUS  current
	            DESCRIPTION
	                    "0. disable 
	                     1. enable"
	            ::= { tplinkSslMIBObjects 7 }

      	    tpHttpsSessionTimeOut	OBJECT-TYPE
			SYNTAX		INTEGER (5..30)
			MAX-ACCESS	read-write
			STATUS		current
			DESCRIPTION	"HTTPS session timeout in minutes."
	            ::= { tplinkSslMIBObjects 8 }
			
			tpHttpsUserLimitEnable	OBJECT-TYPE
			SYNTAX  INTEGER{
					disable(0),
					enable(1)
					}
			MAX-ACCESS	read-write
			STATUS		current
			DESCRIPTION
						"0. disable
						1.enable"
	            ::= { tplinkSslMIBObjects 9 }
				
			tpHttpsUserLimitMaxAdminNum	OBJECT-TYPE
			SYNTAX  INTEGER
			MAX-ACCESS	read-write
			STATUS		current
			DESCRIPTION	"The max num of users as Admin. You should enable HTTPS user number limiting before setting this object."
	            ::= { tplinkSslMIBObjects 10 }
				
			tpHttpsUserLimitMaxOperatorNum	OBJECT-TYPE
			SYNTAX  INTEGER
			MAX-ACCESS	read-write
			STATUS		current
			DESCRIPTION "The max num of users as Operator. You should enable HTTP user number limiting before setting this object."
	            ::= { tplinkSslMIBObjects 11 }

			tpHttpsUserLimitMaxPowerUserNum	OBJECT-TYPE
			SYNTAX  INTEGER
			MAX-ACCESS	read-write
			STATUS		current
			DESCRIPTION "The max num of users as Power User. You should enable HTTP user number limiting before setting this object."
	            ::= { tplinkSslMIBObjects 12 }

			tpHttpsUserLimitMaxUserNum	OBJECT-TYPE
			SYNTAX  INTEGER
			MAX-ACCESS	read-write
			STATUS		current
			DESCRIPTION "The max num of users as User. You should enable HTTP user number limiting before setting this object."
	            ::= { tplinkSslMIBObjects 13 }

			tpHttpsPort	OBJECT-TYPE
			SYNTAX		INTEGER (1..65535)
			MAX-ACCESS	read-write
			STATUS		current
			DESCRIPTION	"Secure HTTP server port number."
				::= { tplinkSslMIBObjects 14 }
          END
