-- Performance stp security  config
-- modify history: not change
--    

TLSG5412F-STP-SECURITY-CONFIG-MIB DEFINITIONS ::= BEGIN

          IMPORTS      	 
              OBJECT-TYPE,MODULE-IDENTITY
          	  	         	FROM SNMPv2-SMI
              spanningTreeSecurityConfig	          
          	  	          	FROM TLSG5412F-SPANNING-TREE-MIB;
          	  	          	
       	stpPortDefendConfig MODULE-IDENTITY  
			    	LAST-UPDATED    "200908260000Z"
			    	ORGANIZATION    "TPLINK."
			    	CONTACT-INFO		"www.tplink.com.cn"
			    	DESCRIPTION			"stp port protect."
			    	REVISION        "200908250000Z"
			    	DESCRIPTION
						"Initial version of this MIB module."
			    	::= { spanningTreeSecurityConfig 1 }      	      
      	       
          
           stpPortDefendTable OBJECT-TYPE
              SYNTAX  SEQUENCE OF STPPORTPROTECTENTRY
              MAX-ACCESS  not-accessible
              STATUS  current
              DESCRIPTION
                      "Port defend function is to prevent the devices from any 
                      malicious attack against STP features.."
              ::= { stpPortDefendConfig 1 }

          stpPortDefendEntry OBJECT-TYPE
              SYNTAX  STPPORTPROTECTENTRY
              MAX-ACCESS  not-accessible
              STATUS  current
              DESCRIPTION
                      "An entry contains of the information of a port protection."
              INDEX   { stpDefendPortNumber }
              ::= { stpPortDefendTable 1 }
      
          STPPORTPROTECTENTRY ::=
              SEQUENCE {
                  stpDefendPortNumber
                      INTEGER, 
                  stpLoopDefendEnable
                      INTEGER, 
                  stpRootBridgeDefendEnable
                  		INTEGER,
                  stpTcDefendEnable
                  		INTEGER,
                  stpBPDUDefendEnable
                  		INTEGER,
                  stpBPDUHoldEnable
                  		INTEGER,
                  stpDefendPortLag
                  		OCTET STRING (SIZE (0..255))     
              }
              
          stpDefendPortNumber OBJECT-TYPE
          		SYNTAX  INTEGER 
              MAX-ACCESS  read-only
              STATUS  current
              DESCRIPTION
                      "Displays the port number of the switch."
              ::= { stpPortDefendEntry 1 }
                     
          stpLoopDefendEnable OBJECT-TYPE
              SYNTAX  INTEGER{
	      							disable(0), 				--Disable
	      							enable(1)						--Enable
	      							}
              MAX-ACCESS  read-write
              STATUS  current
              DESCRIPTION
                      "Loop defend is to prevent the loops in the network brought by 
                      recalculating STP because of link failures and network congestions.
                      0. Disable
                      1. Enable"
              ::= { stpPortDefendEntry 2 }
              
          stpRootBridgeDefendEnable OBJECT-TYPE
              SYNTAX  INTEGER{
	      							disable(0), 				--Disable
	      							enable(1)						--Enable
	      							}
              MAX-ACCESS  read-write
              STATUS  current
              DESCRIPTION
                      "Root defend is to prevent wrong network topology change caused by 
                      the role change of the current legal root bridge.
                      0. Disable
                      1. Enable"
              ::= { stpPortDefendEntry 3 }
              
          stpTcDefendEnable OBJECT-TYPE
              SYNTAX  INTEGER{
	      							disable(0), 				--Disable
	      							enable(1)						--Enable
	      							}
              MAX-ACCESS  read-write
              STATUS  current
              DESCRIPTION
                      "TC defend is to prevent the decrease of the performance and stability 
                      of the switch brought by continuously removing MAC address entries upon 
                      receiving TC-BPDUs in the STP network. 
                      0. Disable
                      1. Enable"
              ::= { stpPortDefendEntry 4 }
              
          stpBPDUDefendEnable OBJECT-TYPE
              SYNTAX  INTEGER{
	      							disable(0), 				--Disable
	      							enable(1)						--Enable
	      							}
              MAX-ACCESS  read-write
              STATUS  current
              DESCRIPTION
                      "BPDU defend is to prevent BPDUs flood in the STP network.
                      0. Disable
                      1. Enable"
              ::= { stpPortDefendEntry 5 }
              
          stpBPDUHoldEnable OBJECT-TYPE
              SYNTAX  INTEGER{
	      							disable(0), 				--Disable
	      							enable(1)						--Enable
	      							}
              MAX-ACCESS  read-write
              STATUS  current
              DESCRIPTION
                      "0. Disable
                       1. Enable"
              ::= { stpPortDefendEntry 6 }  
              
           stpDefendPortLag OBJECT-TYPE
          		SYNTAX  OCTET STRING (SIZE (0..255))
              MAX-ACCESS  read-only
              STATUS  current
              DESCRIPTION
                      	"Displays the LAG number which the port belongs to."
              ::= { stpPortDefendEntry 7 } 
              
              
              
              
    stpTcDefendConfig	OBJECT IDENTIFIER ::= {spanningTreeSecurityConfig 2}
      	      
      	      
      	  stpTcDefendThreshold  OBJECT-TYPE
      	  					SYNTAX  INTEGER(1..100)
			              MAX-ACCESS  read-write
			              STATUS  current
			              DESCRIPTION
			                      "Enter a number from 1 to 100. It is the maximum number of the 
			                      TC-BPDUs received by the switch in a TC Protect Cycle."
			              ::= { stpTcDefendConfig 1 }
              
          stpTcDefendTimer OBJECT-TYPE
				             SYNTAX  INTEGER(1..10)
				              MAX-ACCESS  read-write
				              STATUS  current
				              DESCRIPTION
				                     	"Enter a value from 1 to 10 to specify the TC Protect Cycle."
				              ::= { stpTcDefendConfig 2 }
             
          END
