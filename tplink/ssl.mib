TLSG5412F-SSL-MIB DEFINITIONS ::= BEGIN

          IMPORTS
              OBJECT-TYPE
          	  	         	FROM SNMPv2-SMI
              accessSecurity	          
          	  	          	FROM TLSG5412F-SYSTEM-MIB;
      	
      	      ssl		OBJECT IDENTIFIER ::= {accessSecurity 2}
      	      
      	    sslEnable OBJECT-TYPE
	          SYNTAX  INTEGER{
	      		disable(0), 						
	      		enable(1)						
	      		}
	            MAX-ACCESS  read-write
	            STATUS  current
	            DESCRIPTION
	                    "0. disable 
	                     1. enable"
	            ::= { ssl 1 }
             	
          END
