TLSG5412F-ARP-DEFENSE-MIB DEFINITIONS ::= BEGIN

       IMPORTS
       			MODULE-IDENTITY
        	  	         	FROM SNMPv2-SMI
            arpDefense	          
          	  	          FROM TLSG5412F-NET-SECURITY-MIB; 
          	  	          
        arpDetection  			OBJECT IDENTIFIER ::= {arpDefense 1}
        arpDefend 			OBJECT IDENTIFIER ::= {arpDefense 2}
 END
