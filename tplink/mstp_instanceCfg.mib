-- Performance mstp instance config
-- modify history: not change
--    

TLSG5412F-MSTP-INSTANCE-MIB DEFINITIONS ::= BEGIN

          IMPORTS
              OBJECT-TYPE,MODULE-IDENTITY
          	  	         	FROM SNMPv2-SMI
              	mstpInstance	          
          	  	          	FROM TLSG5412F-SPANNING-TREE-MIB;
          	  	          	
         mstpRegionConfig	OBJECT IDENTIFIER ::= {mstpInstance 1} 	  
         
         mstpRegionName OBJECT-TYPE
      	  					SYNTAX OCTET STRING (SIZE (0..255))
			              MAX-ACCESS  read-write
			              STATUS  current
			              DESCRIPTION
			                      "Create a name for MST region identification using up to 32 
			                      characters."
			              ::= { mstpRegionConfig 1 }
              
          mstpRevision OBJECT-TYPE
				             SYNTAX  INTEGER(0..65535)
				              MAX-ACCESS  read-write
				              STATUS  current
				              DESCRIPTION
				                     "Enter the revision from 0 to 65535 for MST region identification."
				              ::= { mstpRegionConfig 2 } 
				              
				              
				                    	        	
       		
       		mstpInstanceConfig MODULE-IDENTITY  
								    LAST-UPDATED    "200908260000Z"
								    ORGANIZATION    "TPLINK"
								    CONTACT-INFO		"www.tplink.com.cn"
								    DESCRIPTION
								             "Instance Configuration, a property of MST region, is used 
								             to describe the VLAN-to-spanning-tree mapping configuration. 
								             You can assign VLAN to different instances appropriate to 
								             your needs. Every instance is a VLAN group independent of 
								             other instances and CST."
								    REVISION        "200908260000Z"
								    DESCRIPTION
										" mstp instance."
								    ::= { mstpInstance 2 }      	      					      	 
          
          
          mstpInstanceConfigTable OBJECT-TYPE
		              SYNTAX  SEQUENCE OF MSTPINSTANCECONFIGENTRY
		              MAX-ACCESS  not-accessible
		              STATUS  current
		              DESCRIPTION
		                      "Here you can set the VLAN-to-spanning-tree mapping configuration."
		              ::= { mstpInstanceConfig 1 }

          mstpInstanceConfigEntry OBJECT-TYPE
		              SYNTAX  MSTPINSTANCECONFIGENTRY
		              MAX-ACCESS  not-accessible
		              STATUS  current
		              DESCRIPTION
		                      "An entry contains of the mstp instance."
		              INDEX   { mstpInstanceId }
		              ::= { mstpInstanceConfigTable 1 }
      
          MSTPINSTANCECONFIGENTRY ::=
		              SEQUENCE {
		                 	mstpInstanceId
		              				INTEGER,
		                  mstpInstanceEnable
		                      INTEGER,
		                  mstpInstancePRI
		                  		INTEGER,
		                  mstpInstanceVlanId
		                  		OCTET STRING (SIZE (0..255)),
		                  mstpClearInstanceVlanId
		                  		INTEGER
                  
                  
              }
              
         mstpInstanceId OBJECT-TYPE
	           		SYNTAX  INTEGER 
	              MAX-ACCESS  read-only
	              STATUS  current
	              DESCRIPTION
	                      "Displays Instance ID of the switch,0 representative CIST. "
	              ::= { mstpInstanceConfigEntry 1 }
                     
       mstpInstanceEnable OBJECT-TYPE
            	SYNTAX  INTEGER{
	      							disable(0), 					--Disable
	      							enable(1)							--Enable
	      							}
              MAX-ACCESS  read-write
              STATUS  current
              DESCRIPTION
                      "Select Enable/Disable the instance.
                      0. Disable
                      1. Enable"
              ::= { mstpInstanceConfigEntry 2 }
        
       mstpInstancePRI OBJECT-TYPE
            	SYNTAX  INTEGER 
              MAX-ACCESS  read-write
              STATUS  current
              DESCRIPTION
                      "Enter the priority of the switch in the instance. It is an 
                      important criterion on determining if the switch will be 
                      chosen as the root bridge in the specific instance.Make sure 
                      that Priority ranges from 0 to 61440 and could be divided 
                      exactly by 4096"
              ::= { mstpInstanceConfigEntry 3 }
              
      mstpInstanceVlanId OBJECT-TYPE
              SYNTAX OCTET STRING  (SIZE (0..255)) 
              MAX-ACCESS  read-write
              STATUS  current
              DESCRIPTION
                      "Enter the desired VLAN ID. After modification here, the new VLAN 
                      ID will be added to the corresponding instance ID and the previous 
                      VLAN ID won't be replaced.The format of input VLAN ID should be like 
                      '1, 3, 4-7, 11-30' in the range from 1 to 4094."
              ::= { mstpInstanceConfigEntry 4 } 
     mstpClearInstanceVlanId OBJECT-TYPE
				     	SYNTAX				
				   				INTEGER
				   				{
				   					clear(1)
				   				}
				   			MAX-ACCESS		read-write
				   			STATUS				current
				   			DESCRIPTION		
				   			"This object use to clear instance's vlan id.The cleared VLAN ID will 
				   			be automatically mapped to the CIST."
				   			::=	{mstpInstanceConfigEntry 5}
				              
              
        mstpInstancePortConfigTable OBJECT-TYPE
              SYNTAX  SEQUENCE OF MSTPINSTANCEPORTCONFIGENTRY
              MAX-ACCESS  not-accessible
              STATUS  current
              DESCRIPTION
                      "A port can play different roles in different spanning tree instance. 
                      Here you can configure the parameters of the ports in different 
                      instance IDs as well as view status of the ports in the specified instance. "
              ::= { mstpInstanceConfig 2 }
              
        mstpInstancePortConfigEntry OBJECT-TYPE
              SYNTAX  MSTPINSTANCEPORTCONFIGENTRY
              MAX-ACCESS  not-accessible
              STATUS  current
              DESCRIPTION
                      "An entry contains of the mstp instance port config."
              INDEX   { mstpInstancePortConfigId, mstpInstancePortNumber}
              ::= { mstpInstancePortConfigTable 1 }
      
          MSTPINSTANCEPORTCONFIGENTRY ::=
              SEQUENCE {
              		mstpInstancePortConfigId
              				INTEGER,
              		mstpInstancePortNumber
              				INTEGER,
                  mstpInstancePortPRI
                      INTEGER,
                  mstpInstancePortPathCost
                  		INTEGER,
                  mstpInstancePortRole
                  		INTEGER,
                  mstpInstancePortStatus
                  		INTEGER,
                  mstpInstancePortLag
                  		OCTET STRING (SIZE (0..255))
              }
              
          mstpInstancePortConfigId OBJECT-TYPE
          		SYNTAX  INTEGER 
              MAX-ACCESS  read-only
              STATUS  current
              DESCRIPTION
                      "The instance ID for its port configuration,1-8."
              ::= { mstpInstancePortConfigEntry 1}
              
          mstpInstancePortNumber OBJECT-TYPE
          		SYNTAX  INTEGER 
              MAX-ACCESS  read-only
              STATUS  current
              DESCRIPTION
                      "Displays the port number of the switch."
              ::= { mstpInstancePortConfigEntry 2}
                     
          mstpInstancePortPRI OBJECT-TYPE
                SYNTAX  INTEGER(0..240)
              MAX-ACCESS  read-create
              STATUS  current
              DESCRIPTION
                      "Enter the priority of the port in the instance. It is an 
                      important criterion on determining if the port will be chosen 
                      as the root port by the device connected to this port."
              ::= { mstpInstancePortConfigEntry 3 }
             
          mstpInstancePortPathCost OBJECT-TYPE
              SYNTAX  INTEGER (0..2000000)
              MAX-ACCESS  read-write
              STATUS  current
              DESCRIPTION
                      "Path Cost is used to choose the path and calculate the path costs 
                      of ports in an MST region. It is an important criterion on determining 
                      the root port. The lower value has the higher priority."
              ::= { mstpInstancePortConfigEntry 4 }
                            
        mstpInstancePortRole OBJECT-TYPE
		        SYNTAX  INTEGER{
		  							disabled(1), 				--Disable
		  							alternate(2),				--Alternate
		  							backup(3),					--Backup
		  							designated(4),			--Designated
		  							root(5),						--root
		  							master(6)						--Master
		  							}
		        MAX-ACCESS  read-only
		        STATUS  current
		        DESCRIPTION
		                "Displays the role of the port played in the STP Instance.
		                1. Disable
		                2. Alternate
		                3. Backup
		                4. Designated
		                5. root
		                6. Master"
		        ::= { mstpInstancePortConfigEntry 5 }
		        
		    mstpInstancePortStatus OBJECT-TYPE
		        SYNTAX  INTEGER{
		  							disabled(1), 				--Disable
		  							blocking(2),				--Blocking
		  							learning(3),				--Learning
		  							forwarding(4)				--Forwarding
		  							}
		        MAX-ACCESS  read-only
		        STATUS  current
		        DESCRIPTION
		                "Displays the working status of the port.
		                1. Disable
		                2. Blocking
		                3. Learning
		                4. Forwarding"
		        ::= { mstpInstancePortConfigEntry 6 }
		        
		     mstpInstancePortLag OBJECT-TYPE
          		SYNTAX  OCTET STRING (SIZE (0..255)) 
              MAX-ACCESS  read-only
              STATUS  current
              DESCRIPTION
                      "Displays the LAG number which the port belongs to."
              ::= { mstpInstancePortConfigEntry 7 }
              
               	
          END
