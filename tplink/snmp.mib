TLSG5412F-SNMP-MIB DEFINITIONS ::= BEGIN

         IMPORTS
            MODULE-IDENTITY
          	  	         	FROM SNMPv2-SMI
            tlsg5412f	          
          	  	          FROM TPLINK; 
          	  	          
          	 
	    snmpControl MODULE-IDENTITY
	    LAST-UPDATED    "200908190000Z"
	    ORGANIZATION    "TPLINK"
	    CONTACT-INFO    "www.tplink.com.cn"
	    DESCRIPTION
	             "Private MIB for snmp config."
	    REVISION        "200908190000Z"
	    DESCRIPTION
	            "Initial version of this MIB module."
	    ::= { tlsg5412f 9 }
	    
		snmpNotifyCtrl	OBJECT IDENTIFIER ::= {snmpControl 1}
		snmpRmon	OBJECT IDENTIFIER ::= {snmpControl 2}
  	
END
