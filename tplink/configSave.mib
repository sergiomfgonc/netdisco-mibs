TLSG5412F-CONFIGSAVE-MIB DEFINITIONS ::= BEGIN

          IMPORTS
            OBJECT-TYPE,MODULE-IDENTITY
          	  	         	FROM SNMPv2-SMI
              tlsg5412f	          
          	  	          	FROM TPLINK; 
 	    configSave MODULE-IDENTITY
	    LAST-UPDATED    "200907090000Z"
	    ORGANIZATION    "system"
	    CONTACT-INFO
	            " www.tplink.com.cn"
	    DESCRIPTION
	             "TPLINK Private MIB for config mange."
	    REVISION        "200812150000Z"
	    DESCRIPTION
	            "Initial version of this MIB module."
	    ::= { tlsg5412f 11 }         	  	          
        	 
   		save		OBJECT-TYPE
   			SYNTAX				
   				INTEGER
   				{
   					commit(1)
   				}
   			MAX-ACCESS		read-write
   			STATUS				current
   			DESCRIPTION		
   			"This object use to save the current config."
   			::=	{configSave 1}
END
