TLSG5412F-SERVICE-QUALITY-MIB DEFINITIONS ::= BEGIN

       IMPORTS
       			MODULE-IDENTITY
        	  	         	FROM SNMPv2-SMI
            tlsg5412f	          
          	  	          FROM TPLINK; 
          	  	          
      serviceQuality MODULE-IDENTITY
	    LAST-UPDATED    "200908190000Z"
	    ORGANIZATION    "TPLINK"
	    CONTACT-INFO
	            " www.tplink.com.cn"
	    DESCRIPTION
	             "Private MIB for service Quality config."
	    REVISION        "200908190000Z"
	    DESCRIPTION
	            "Initial version of this MIB module."
	    ::= { tlsg5412f 6 }
	    
			 	qos  	OBJECT IDENTIFIER ::= {serviceQuality 1}
        bandWidth 	OBJECT IDENTIFIER ::= {serviceQuality 2}
        voiceVlan 	OBJECT IDENTIFIER ::= {serviceQuality 3}
 		notifications 	OBJECT IDENTIFIER ::= {serviceQuality 4}  
        
        broadcastRateExceed NOTIFICATION-TYPE  
        	OBJECTS 
			{
				StormControlPort,
				StormControlBroadCastRate			
			}

           	STATUS          current
    		DESCRIPTION 
    			"An broasdcastRateExceed notification is sent when the value
        of broadcast stormControl rate set of port is exceeded.                        
        
        		Note that if you need this notification, the value of broadcast 
        stormControl rate of port must be set. The transmission of 
        stormControl notifications are throttled by the agent three sesonds 
        every time."
    		::= { notifications 1}       
    		
    	multicastRateExceed NOTIFICATION-TYPE  
        	OBJECTS 
			{
				StormControlPort,
				StormControlMultiCastRate			
			}

           	STATUS          current
    		DESCRIPTION 
    			"An stormControl notification is sent when the value
        of multicast stormControl rate set of port is exceeded.                        
        
        		Note that if you need this notification, the value of multicast 
        stormControl rate of port must be set. The transmission of 
        stormControl notifications are throttled by the agent three sesonds 
        every time."
    		::= { notifications 2}

    		
        ingressRateExceed NOTIFICATION-TYPE 
			OBJECTS 
			{
				rateLimitPort,
				rateLimitIngressRate
			}
           	STATUS          current
    		DESCRIPTION 
    			"An ingressRateExceed notification is sent when the value
        of ingress rate set of port is exceeded.                        
        
        		Note that if you need this notification, the value of ingress 
        rate of port must be set.The transmission of ingressRateExceed 
        notifications are throttled by the agent three sesonds every time."
    		::= { notifications 3}
        egressRateExceed NOTIFICATION-TYPE 
			OBJECTS 
			{
				rateLimitPort,
				rateLimitEgressRate
			}
           	STATUS          current
    		DESCRIPTION 
    			"An egressRateExceed notification is sent when the value
         of egress rate set of port is exceeded.                        
        
        		Note that if you need this notification, the value of egress 
         rate of port must be set.The transmission of egressRateExceed 
         notifications are throttled by the agent three sesonds every time."
    		::= { notifications 4}      
        
 END
