-- Performance spanning tree
                                                              


 TLSG5412F-SPANNING-TREE-MIB DEFINITIONS ::= BEGIN

          IMPORTS
             
             MODULE-IDENTITY
          	  	         	FROM SNMPv2-SMI
              tlsg5412f	          
          	  	          	FROM TPLINK; 
          	  	          
          	 
	    spanningTree MODULE-IDENTITY
	    LAST-UPDATED    "200907090000Z"
	    ORGANIZATION    "TPLINK"
	    CONTACT-INFO		" www.tplink.com.cn"
	    DESCRIPTION
	             "Private MIB for spanning tree."
	    REVISION        "200812150000Z"
	    DESCRIPTION
	            "Initial version of this MIB module."
	    ::= { tlsg5412f 4 }

          spanningTreeBasicConfig   OBJECT IDENTIFIER ::= {spanningTree 1}
          spanningTreePortConfig 		OBJECT IDENTIFIER ::= {spanningTree 2}
	  			mstpInstance							OBJECT IDENTIFIER ::= {spanningTree 3}
	  			spanningTreeSecurityConfig	OBJECT IDENTIFIER ::= {spanningTree 4}
		spanningTreeNotifications	OBJECT IDENTIFIER ::= {spanningTree 5}
	  			
  			mstpTopologyChange NOTIFICATION-TYPE
	        	OBJECTS
	        	{
	        	}
	        	STATUS current
	        	DESCRIPTION 
	        		"The topology of spanning tree has changed."
	            ::= {spanningTreeNotifications 1}
	  			
          END
