--   Performance multicast manage
                                                              


 TLSG5412F-IGMP-MANAGE-MIB DEFINITIONS ::= BEGIN

          IMPORTS
             
             MODULE-IDENTITY
          	  	         	FROM SNMPv2-SMI
              tlsg5412f	          
          	  	          	FROM TPLINK; 
          	  	          
          	 
	    multicastManage MODULE-IDENTITY
	    LAST-UPDATED    "200908270000Z"
	    ORGANIZATION    "TPLINK"
	    CONTACT-INFO  	"www.tplink.com.cn"
	    DESCRIPTION
	             "Private MIB for igmp manage."
	    REVISION        "200908270000Z"
	    DESCRIPTION
	            "Initial version of this MIB module."
	    ::= { tlsg5412f 5 }

          igmpSnooping   					OBJECT IDENTIFIER ::= {multicastManage 1}
	  			igmpFilter					OBJECT IDENTIFIER ::= {multicastManage 2}
	  			igmpPacketStatistic			OBJECT IDENTIFIER ::= {multicastManage 3} 
	  			igmpMultigroup                          OBJECT IDENTIFIER ::= {multicastManage 4}
	  			igmpStaticMultigroup                    OBJECT IDENTIFIER ::= {multicastManage 5}
          END
