TLSG5412F-PORTISOLATION-MIB DEFINITIONS ::= BEGIN
		IMPORTS
		  OBJECT-TYPE,MODULE-IDENTITY
			  	         	FROM SNMPv2-SMI     	  	         	
			l2PortManage
										FROM TLSG5412F-L2SWITCH-MIB;
										
			l2PortIsolation MODULE-IDENTITY  
	    LAST-UPDATED    "200908270000Z"
	    ORGANIZATION    "TPLINK"
	    CONTACT-INFO		"www.tplink.com.cn"
	    DESCRIPTION			"The config of the port mirror."
	    REVISION        "200908270000Z"
	    DESCRIPTION			"Initial version of this MIB module."
	    ::= { l2PortManage 4 }
																										          	  	          
	   		portIsolationCtrlTable OBJECT-TYPE
              SYNTAX  SEQUENCE OF PORTISOLATIONCTRLENTRY
              MAX-ACCESS  not-accessible
              STATUS  current
              DESCRIPTION
                      "A list of port isolation."
              ::= { l2PortIsolation 1 }
         portIsolationCtrlEntry OBJECT-TYPE
              SYNTAX  PORTISOLATIONCTRLENTRY
              MAX-ACCESS  not-accessible
              STATUS  current
              DESCRIPTION
                      "The entry of the port isolation list ."
              INDEX   { portIsolationPortId }
              ::= { portIsolationCtrlTable 1 }
              
              
        PORTISOLATIONCTRLENTRY ::=
              SEQUENCE {
                  portIsolationPortId
                      INTEGER, 
                  portIsolationForList
                  		OCTET STRING (SIZE (0..255)),
                  portIsolationTrunkId
                  		INTEGER
              }
              
         portIsolationPortId  OBJECT-TYPE
			     SYNTAX  INTEGER  
			      MAX-ACCESS  read-only
			      STATUS  current
			      DESCRIPTION
			              "The port id."
			      ::= { portIsolationCtrlEntry 1 }
			      
			    portIsolationForList  OBJECT-TYPE
			     SYNTAX  OCTET STRING (SIZE (0..255))  
			      MAX-ACCESS  read-write
			      STATUS  current
			      DESCRIPTION
			              "The forward port list,such as 1-5,9-11,16."
			      ::= { portIsolationCtrlEntry 2 }
			      
			    portIsolationTrunkId  OBJECT-TYPE
			     SYNTAX  INTEGER  
			      MAX-ACCESS  read-only
			      STATUS  current
			      DESCRIPTION
			              "The trunk id of the port."
			      ::= { portIsolationCtrlEntry 3 }
			      
END
