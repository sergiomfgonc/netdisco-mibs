TLSG3424-HTTP-MIB DEFINITIONS ::= BEGIN

		IMPORTS
			OBJECT-TYPE,MODULE-IDENTITY
				FROM SNMPv2-SMI
			accessSecurity	          
          	  	FROM TLSG3424-SYSTEM-MIB;
      	
		http	OBJECT IDENTIFIER ::= {accessSecurity 3}
				
		httpEnable	OBJECT-TYPE
			SYNTAX  INTEGER{
					disable(0),
					enable(1)
					}
			MAX-ACCESS  read-write
			STATUS  current
			DESCRIPTION
					"0. disable
					1. enable"
			::= { http 1 }

        httpSessionTimeOut	OBJECT-TYPE
			SYNTAX		INTEGER (5..30)
			MAX-ACCESS	read-write
			STATUS		current
			DESCRIPTION	"HTTP session timeout in minutes."
			::= { http 2 }

		httpUserLimitEnable	OBJECT-TYPE
			SYNTAX  INTEGER{
					disable(0),
					enable(1)
					}
			MAX-ACCESS	read-write
			STATUS		current
			DESCRIPTION
						"0. disable
						1.enable"
			::= { http 3 }

		httpUserLimitMaxAdminNum	OBJECT-TYPE
			SYNTAX  INTEGER
			MAX-ACCESS	read-write
			STATUS		current
			DESCRIPTION	"The max num of admin users. You should enable HTTP user number limiting before setting this object."
			::= { http 4 }

		httpUserLimitMaxGuestNum	OBJECT-TYPE
			SYNTAX  INTEGER
			MAX-ACCESS	read-write
			STATUS		current
			DESCRIPTION "The max num of guest users. You should enable HTTP user number limiting before setting this object."
			::= { http 5 }

		END
