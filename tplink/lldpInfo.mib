TLSG5412F-LLDPINFO-MIB DEFINITIONS ::= BEGIN
       
       IMPORTS
            OBJECT-TYPE,IpAddress
          	  	         	FROM SNMPv2-SMI
            lldpInfo
					FROM TLSG5412F-LLDP-MIB;
	
			lldpLocalInfoTable OBJECT-TYPE
              SYNTAX  SEQUENCE OF LLDPLOCALINFOENTRY
              MAX-ACCESS  not-accessible
              STATUS  current
              DESCRIPTION
                      "Local port information entries."
              ::= { lldpInfo 1 }

          lldpLocalInfoEntry OBJECT-TYPE
              SYNTAX  LLDPLOCALINFOENTRY
              MAX-ACCESS  not-accessible
              STATUS  current
              DESCRIPTION
                      "An entry contains of the information of local port of the switch."
              INDEX   { lldpLocalPortId }
              ::= { lldpLocalInfoTable 1 }
      
          LLDPLOCALINFOENTRY ::=
              SEQUENCE {
              		lldpLocalPortId
              				INTEGER,
                  lldpLocalChassisIdType
                  		OCTET STRING (SIZE (0..255)),
                  lldpLocalChassisId
                      OCTET STRING (SIZE (0..255)),
                  lldpLocalPortIdType
                      OCTET STRING (SIZE (0..255)),
                  lldpLocalPortIdDescr
                      OCTET STRING (SIZE (0..255)),
                  lldpLocalTtl
                      INTEGER,
                  lldpLocalPortDescr
                      OCTET STRING (SIZE (0..255)),
                  lldpLocalDeviceName
                      OCTET STRING (SIZE (0..255)),
                  lldpLocalDeviceDescr
                      OCTET STRING (SIZE (0..255)),
                  lldpLocalCapAvailable
                      OCTET STRING (SIZE (0..255)),
                  lldpLocalCapEnabled
                      OCTET STRING (SIZE (0..255)),
                  lldpLocalManageIpAddr
                      IpAddress,
                  lldpLocalManageAddrType
                      OCTET STRING (SIZE (0..255)),
                  lldpLocalManageAddrInterfaceType
                      OCTET STRING (SIZE (0..255)),
                  lldpLocalManageAddrInterfaceId
                      INTEGER,
                  lldpLocalManageAddrOID
                      INTEGER,
				  lldpLocalPortAndProtocolVlanID
					  OCTET STRING (SIZE (0..255)),
				  lldpLocalVlanName
					  OCTET STRING (SIZE (0..255)),
                  lldpLocalAutoNegotiationSupported
                      INTEGER,
                  lldpLocalAutoNegotiationEnabled
                      INTEGER,
                  lldpLocalOperMau
                      OCTET STRING (SIZE (0..255)),
                  lldpLocalLinkAggregationSupported
                      INTEGER,
                  lldpLocalLinkAggregationEnabled
                      INTEGER,
                  lldpLocalAggregationPortId
                      INTEGER,
                  lldpLocalPowerPortClass
                      OCTET STRING (SIZE (0..255)),
                  lldpLocalPsePowerSupported
                      INTEGER,
                  lldpLocalPsePowerEnabled
                      INTEGER,
                  lldpLocalPsePairsControlAbility
                      INTEGER,
                  lldpLocalMaximumFrameSize
                      INTEGER                      
              	}
              	
              
          lldpLocalPortId OBJECT-TYPE
            	SYNTAX  INTEGER  
              MAX-ACCESS  read-only
              STATUS  current
              DESCRIPTION
                      "Displays the port index."
              ::= { lldpLocalInfoEntry 1 }
              
          lldpLocalChassisIdType OBJECT-TYPE
            	SYNTAX  OCTET STRING (SIZE (0..255))  
              MAX-ACCESS  read-only
              STATUS  current
              DESCRIPTION
                      "Displays the type of the chassis ID."
              ::= { lldpLocalInfoEntry 2 }
                     
          lldpLocalChassisId OBJECT-TYPE
            	SYNTAX  OCTET STRING (SIZE (0..255))  
              MAX-ACCESS  read-only
              STATUS  current
              DESCRIPTION
                      "Displays the chassis ID."
              ::= { lldpLocalInfoEntry 3 }
            
          lldpLocalPortIdType OBJECT-TYPE
            	SYNTAX  OCTET STRING (SIZE (0..255))  
              MAX-ACCESS  read-only
              STATUS  current
              DESCRIPTION
                      "Displays the type of the port ID."
              ::= { lldpLocalInfoEntry 4 }
           
          lldpLocalPortIdDescr OBJECT-TYPE
            	SYNTAX  OCTET STRING (SIZE (0..255))  
              MAX-ACCESS  read-only
              STATUS  current
              DESCRIPTION
                      "Displays the description of the port ID."
              ::= { lldpLocalInfoEntry 5 }
              
          lldpLocalTtl OBJECT-TYPE
            	SYNTAX  INTEGER 
              MAX-ACCESS  read-only
              STATUS  current
              DESCRIPTION
                      "Displays the TTL."
              ::= { lldpLocalInfoEntry 6 }
              
          lldpLocalPortDescr OBJECT-TYPE
            	SYNTAX  OCTET STRING (SIZE (0..255))  
              MAX-ACCESS  read-only
              STATUS  current
              DESCRIPTION
                      "Displays the port description."
              ::= { lldpLocalInfoEntry 7 }
              
          lldpLocalDeviceName OBJECT-TYPE
            	SYNTAX  OCTET STRING (SIZE (0..255))  
              MAX-ACCESS  read-only
              STATUS  current
              DESCRIPTION
                      "Displays the system name."
              ::= { lldpLocalInfoEntry 8 }
              
          lldpLocalDeviceDescr OBJECT-TYPE
            	SYNTAX  OCTET STRING (SIZE (0..255))  
              MAX-ACCESS  read-only
              STATUS  current
              DESCRIPTION
                      "Displays the system description."
              ::= { lldpLocalInfoEntry 9 }
              
          lldpLocalCapAvailable OBJECT-TYPE
            	SYNTAX  OCTET STRING (SIZE (0..255))  
              MAX-ACCESS  read-only
              STATUS  current
              DESCRIPTION
                      "Displays the system capabilities supported."
              ::= { lldpLocalInfoEntry 10 }
              
          lldpLocalCapEnabled OBJECT-TYPE
            	SYNTAX  OCTET STRING (SIZE (0..255))  
              MAX-ACCESS  read-only
              STATUS  current
              DESCRIPTION
                      "Displays the system capabilities enabled."
              ::= { lldpLocalInfoEntry 11 }
              
          lldpLocalManageIpAddr OBJECT-TYPE
            	SYNTAX  IpAddress  
              MAX-ACCESS  read-only
              STATUS  current
              DESCRIPTION
                      "Displays the management address."
              ::= { lldpLocalInfoEntry 12 }
       
           lldpLocalManageAddrType OBJECT-TYPE
            	SYNTAX  OCTET STRING (SIZE (0..255))  
              MAX-ACCESS  read-only
              STATUS  current
              DESCRIPTION
                      "Displays the management address type."
              ::= { lldpLocalInfoEntry 13 }
              
          lldpLocalManageAddrInterfaceType OBJECT-TYPE
            	SYNTAX  OCTET STRING (SIZE (0..255))  
              MAX-ACCESS  read-only
              STATUS  current
              DESCRIPTION
                      "Displays the management address interface type."
              ::= { lldpLocalInfoEntry 14 }
       
          lldpLocalManageAddrInterfaceId OBJECT-TYPE
            	SYNTAX  INTEGER 
              MAX-ACCESS  read-only
              STATUS  current
              DESCRIPTION
                      "Displays the management address interface ID."
              ::= { lldpLocalInfoEntry 15 }
              
          lldpLocalManageAddrOID OBJECT-TYPE
            	SYNTAX  INTEGER 
              MAX-ACCESS  read-only
              STATUS  current
              DESCRIPTION
                      "Displays the management address OID."
              ::= { lldpLocalInfoEntry 16 }         
              
          lldpLocalPortAndProtocolVlanID OBJECT-TYPE
            	SYNTAX  OCTET STRING (SIZE (0..255)) 
              MAX-ACCESS  read-only
              STATUS  current
              DESCRIPTION
                      "Displays the port and protocol VLAN ID."
              ::= { lldpLocalInfoEntry 17 } 
			  
           lldpLocalVlanName OBJECT-TYPE
            	SYNTAX  OCTET STRING (SIZE (0..255)) 
              MAX-ACCESS  read-only
              STATUS  current
              DESCRIPTION
                      "Displays the port and protocol VLAN ID."
              ::= { lldpLocalInfoEntry 18 }                   
              
          lldpLocalAutoNegotiationSupported OBJECT-TYPE
            	SYNTAX  INTEGER {
	      							disable(0), 						--disable
	      							enable(1)								--enable
	      							}
              MAX-ACCESS  read-only
              STATUS  current
              DESCRIPTION
                      "Displays the supported state of the auto-negotiation ."
              ::= { lldpLocalInfoEntry 19 } 
              
          lldpLocalAutoNegotiationEnabled OBJECT-TYPE
            	SYNTAX  INTEGER {
	      							disable(0), 						--disable
	      							enable(1)								--enable
	      							}
              MAX-ACCESS  read-only
              STATUS  current
              DESCRIPTION
                      "Displays the enabled state of the auto-negotiation ."
              ::= { lldpLocalInfoEntry 20 } 
              
          lldpLocalOperMau OBJECT-TYPE
            	SYNTAX  OCTET STRING (SIZE (0..255)) 
              MAX-ACCESS  read-only
              STATUS  current
              DESCRIPTION
                      "Displays the speed and duplex mode for the port."
              ::= { lldpLocalInfoEntry 21 } 
              
          lldpLocalLinkAggregationSupported OBJECT-TYPE
            	SYNTAX  INTEGER {
	      							disable(0), 						--disable
	      							enable(1)								--enable
	      							}
              MAX-ACCESS  read-only
              STATUS  current
              DESCRIPTION
                      "Displays the supported state of the link aggregation ."
              ::= { lldpLocalInfoEntry 22 } 
              
          lldpLocalLinkAggregationEnabled OBJECT-TYPE
            	SYNTAX  INTEGER {
	      							disable(0), 						--disable
	      							enable(1)								--enable
	      							}
              MAX-ACCESS  read-only
              STATUS  current
              DESCRIPTION
                      "Displays the enabled state of the link aggregation ."
              ::= { lldpLocalInfoEntry 23 } 
              
          lldpLocalAggregationPortId OBJECT-TYPE
            	SYNTAX  INTEGER
              MAX-ACCESS  read-only
              STATUS  current
              DESCRIPTION
                      "Displays the aggregation port id ."
              ::= { lldpLocalInfoEntry 24 } 
              
          lldpLocalPowerPortClass OBJECT-TYPE
            	SYNTAX  OCTET STRING (SIZE (0..255)) 
              MAX-ACCESS  read-only
              STATUS  current
              DESCRIPTION
                      "Displays the power port class."
              ::= { lldpLocalInfoEntry 25 } 
              
          lldpLocalPsePowerSupported OBJECT-TYPE
            	SYNTAX  INTEGER {
	      							disable(0), 						--disable
	      							enable(1)								--enable
	      							}
              MAX-ACCESS  read-only
              STATUS  current
              DESCRIPTION
                      "Displays the supported state of the PSE power ."
              ::= { lldpLocalInfoEntry 26 }
              
          lldpLocalPsePowerEnabled OBJECT-TYPE
            	SYNTAX  INTEGER {
	      							disable(0), 						--disable
	      							enable(1)								--enable
	      							}
              MAX-ACCESS  read-only
              STATUS  current
              DESCRIPTION
                      "Displays the enabled state of the PSE power."
              ::= { lldpLocalInfoEntry 27 } 
              
          lldpLocalPsePairsControlAbility OBJECT-TYPE
            	SYNTAX  INTEGER {
	      							disable(0), 						--disable
	      							enable(1)								--enable
	      							}
              MAX-ACCESS  read-only
              STATUS  current
              DESCRIPTION
                      "Displays the enabled state of the PSE pairs control."
              ::= { lldpLocalInfoEntry 28 } 
              
          lldpLocalMaximumFrameSize OBJECT-TYPE
            	SYNTAX  INTEGER 
              MAX-ACCESS  read-only
              STATUS  current
              DESCRIPTION
                      "Displays the size of the maximum frame."
              ::= { lldpLocalInfoEntry 29 } 
       
       
       lldpNeighborInfoTable OBJECT-TYPE
              SYNTAX  SEQUENCE OF LLDPNEIGHBORINFOENTRY
              MAX-ACCESS  not-accessible
              STATUS  current
              DESCRIPTION
                      "Neighbor port information  entries."
              ::= { lldpInfo 2 }

          lldpNeighborInfoEntry OBJECT-TYPE
              SYNTAX  LLDPNEIGHBORINFOENTRY
              MAX-ACCESS  not-accessible
              STATUS  current
              DESCRIPTION
                      "An entry contains of the information of neighbor port of the switch."
              INDEX   { lldpNeighborPortId , lldpNeighborPortIndexId}
              ::= { lldpNeighborInfoTable 1 }
      
          LLDPNEIGHBORINFOENTRY ::=
              SEQUENCE {
              		lldpNeighborPortId
              				INTEGER,
              		lldpNeighborPortIndexId
              				INTEGER,
                  lldpNeighborChassisIdType
                  		OCTET STRING (SIZE (0..255)),
                  lldpNeighborChassisId
                      OCTET STRING (SIZE (0..255)),
                  lldpNeighborPortIdType
                      OCTET STRING (SIZE (0..255)),
                  lldpNeighborPortIdDescr
                      OCTET STRING (SIZE (0..255)),
                  lldpNeighborTtl
                      INTEGER,
                  lldpNeighborPortDescr
                      OCTET STRING (SIZE (0..255)),
                  lldpNeighborDeviceName
                      OCTET STRING (SIZE (0..255)),
                  lldpNeighborDeviceDescr
                      OCTET STRING (SIZE (0..255)),
                  lldpNeighborCapAvailable
                      OCTET STRING (SIZE (0..255)),
                  lldpNeighborCapEnabled
                      OCTET STRING (SIZE (0..255)),
                  lldpNeighborManageIpAddr
                      IpAddress,
                  lldpNeighborManageAddrType
                      OCTET STRING (SIZE (0..255)),
                  lldpNeighborManageAddrInterfaceType
                      OCTET STRING (SIZE (0..255)),
                  lldpNeighborManageAddrInterfaceId
                      INTEGER,
                  lldpNeighborManageAddrOID
                      INTEGER,
				  lldpNeighborPortAndProtocolVlanID
					  OCTET STRING (SIZE (0..512)),
				  lldpNeighborVlanName
					  OCTET STRING (SIZE (0..512)),
				  lldpNeighborProtocolIdentity
					  OCTET STRING (SIZE (0..512)),
                  lldpNeighborAutoNegotiationSupported
                      INTEGER,
                  lldpNeighborAutoNegotiationEnabled
                      INTEGER,
                  lldpNeighborOperMau
                      OCTET STRING (SIZE (0..255)),
                  lldpNeighborLinkAggregationSupported
                      INTEGER,
                  lldpNeighborLinkAggregationEnabled
                      INTEGER,
                  lldpNeighborAggregationPortId
                      INTEGER,
                  lldpNeighborPowerPortClass
                      OCTET STRING (SIZE (0..255)),
                  lldpNeighborPsePowerSupported
                      INTEGER,
                  lldpNeighborPsePowerEnabled
                      INTEGER,
                  lldpNeighborPsePairsControlAbility
                      INTEGER,
                  lldpNeighborMaximumFrameSize
                      INTEGER                   
              	}              	
              
          lldpNeighborPortId OBJECT-TYPE
            	SYNTAX  INTEGER  
              MAX-ACCESS  read-only
              STATUS  current
              DESCRIPTION
                      "Displays the port index."
              ::= { lldpNeighborInfoEntry 1 }
              
          lldpNeighborPortIndexId OBJECT-TYPE
            	SYNTAX  INTEGER  
              MAX-ACCESS  read-only
              STATUS  current
              DESCRIPTION
                      "Displays the neighbor index."
              ::= { lldpNeighborInfoEntry 2 }
              
          lldpNeighborChassisIdType OBJECT-TYPE
            	SYNTAX  OCTET STRING (SIZE (0..255))  
              MAX-ACCESS  read-only
              STATUS  current
              DESCRIPTION
                      "Displays the type of the chassis ID."
              ::= { lldpNeighborInfoEntry 3 }
                     
          lldpNeighborChassisId OBJECT-TYPE
            	SYNTAX  OCTET STRING (SIZE (0..255))  
              MAX-ACCESS  read-only
              STATUS  current
              DESCRIPTION
                      "Displays the chassis ID."
              ::= { lldpNeighborInfoEntry 4 }
            
          lldpNeighborPortIdType OBJECT-TYPE
            	SYNTAX  OCTET STRING (SIZE (0..255))  
              MAX-ACCESS  read-only
              STATUS  current
              DESCRIPTION
                      "Displays the type of the port ID."
              ::= { lldpNeighborInfoEntry 5 }
           
          lldpNeighborPortIdDescr OBJECT-TYPE
            	SYNTAX  OCTET STRING (SIZE (0..255))  
              MAX-ACCESS  read-only
              STATUS  current
              DESCRIPTION
                      "Displays the description of the port ID."
              ::= { lldpNeighborInfoEntry 6 }
              
          lldpNeighborTtl OBJECT-TYPE
            	SYNTAX  INTEGER 
              MAX-ACCESS  read-only
              STATUS  current
              DESCRIPTION
                      "Displays the TTL."
              ::= { lldpNeighborInfoEntry 7 }
              
          lldpNeighborPortDescr OBJECT-TYPE
            	SYNTAX  OCTET STRING (SIZE (0..255))  
              MAX-ACCESS  read-only
              STATUS  current
              DESCRIPTION
                      "Displays the port description."
              ::= { lldpNeighborInfoEntry 8 }
              
          lldpNeighborDeviceName OBJECT-TYPE
            	SYNTAX  OCTET STRING (SIZE (0..255))  
              MAX-ACCESS  read-only
              STATUS  current
              DESCRIPTION
                      "Displays the system name."
              ::= { lldpNeighborInfoEntry 9 }
              
          lldpNeighborDeviceDescr OBJECT-TYPE
            	SYNTAX  OCTET STRING (SIZE (0..255))  
              MAX-ACCESS  read-only
              STATUS  current
              DESCRIPTION
                      "Displays the system description."
              ::= { lldpNeighborInfoEntry 10 }
              
          lldpNeighborCapAvailable OBJECT-TYPE
            	SYNTAX  OCTET STRING (SIZE (0..255))  
              MAX-ACCESS  read-only
              STATUS  current
              DESCRIPTION
                      "Displays the system capabilities supported."
              ::= { lldpNeighborInfoEntry 11 }
              
          lldpNeighborCapEnabled OBJECT-TYPE
            	SYNTAX  OCTET STRING (SIZE (0..255))  
              MAX-ACCESS  read-only
              STATUS  current
              DESCRIPTION
                      "Displays the system capabilities enabled."
              ::= { lldpNeighborInfoEntry 12 }
              
          lldpNeighborManageIpAddr OBJECT-TYPE
            	SYNTAX  IpAddress  
              MAX-ACCESS  read-only
              STATUS  current
              DESCRIPTION
                      "Displays the management address."
              ::= { lldpNeighborInfoEntry 13 }
              
          lldpNeighborManageAddrType OBJECT-TYPE
            	SYNTAX  OCTET STRING (SIZE (0..255))  
              MAX-ACCESS  read-only
              STATUS  current
              DESCRIPTION
                      "Displays the management address type."
              ::= { lldpNeighborInfoEntry 14 }
              
          lldpNeighborManageAddrInterfaceType OBJECT-TYPE
            	SYNTAX  OCTET STRING (SIZE (0..255))  
              MAX-ACCESS  read-only
              STATUS  current
              DESCRIPTION
                      "Displays the management address interface type."
              ::= { lldpNeighborInfoEntry 15 }
       
          lldpNeighborManageAddrInterfaceId OBJECT-TYPE
            	SYNTAX  INTEGER 
              MAX-ACCESS  read-only
              STATUS  current
              DESCRIPTION
                      "Displays the management address interface ID."
              ::= { lldpNeighborInfoEntry 16 }
              
          lldpNeighborManageAddrOID OBJECT-TYPE
            	SYNTAX  INTEGER 
              MAX-ACCESS  read-only
              STATUS  current
              DESCRIPTION
                      "Displays the management address OID."
              ::= { lldpNeighborInfoEntry 17 } 
          
          lldpNeighborPortAndProtocolVlanID OBJECT-TYPE
            	SYNTAX  OCTET STRING (SIZE (0..512)) 
              MAX-ACCESS  read-only
              STATUS  current
              DESCRIPTION
                      "Displays the port and protocol VLAN ID TLV."
              ::= { lldpNeighborInfoEntry 18 } 
 
          lldpNeighborVlanName OBJECT-TYPE
            	SYNTAX  OCTET STRING (SIZE (0..512)) 
              MAX-ACCESS  read-only
              STATUS  current
              DESCRIPTION
                      "Displays the VLAN name TLV."
              ::= { lldpNeighborInfoEntry 19 } 

          lldpNeighborProtocolIdentity OBJECT-TYPE
            	SYNTAX  OCTET STRING (SIZE (0..512)) 
              MAX-ACCESS  read-only
              STATUS  current
              DESCRIPTION
                      "Displays the protocol identity TLV."
              ::= { lldpNeighborInfoEntry 20 } 
			  
          lldpNeighborAutoNegotiationSupported OBJECT-TYPE
            	SYNTAX  INTEGER {
	      							disable(0), 						--disable
	      							enable(1)								--enable
	      							}
              MAX-ACCESS  read-only
              STATUS  current
              DESCRIPTION
                      "Displays the supported state of the auto-negotiation ."
              ::= { lldpNeighborInfoEntry 21 } 
              
          lldpNeighborAutoNegotiationEnabled OBJECT-TYPE
            	SYNTAX  INTEGER {
	      							disable(0), 						--disable
	      							enable(1)								--enable
	      							}
              MAX-ACCESS  read-only
              STATUS  current
              DESCRIPTION
                      "Displays the enabled state of the auto-negotiation ."
              ::= { lldpNeighborInfoEntry 22 } 
              
          lldpNeighborOperMau OBJECT-TYPE
            	SYNTAX  OCTET STRING (SIZE (0..255)) 
              MAX-ACCESS  read-only
              STATUS  current
              DESCRIPTION
                      "Displays the speed and duplex mode for the port."
              ::= { lldpNeighborInfoEntry 23 } 
              
          lldpNeighborLinkAggregationSupported OBJECT-TYPE
            	SYNTAX  INTEGER {
	      							disable(0), 						--disable
	      							enable(1)								--enable
	      							}
              MAX-ACCESS  read-only
              STATUS  current
              DESCRIPTION
                      "Displays the supported state of the link aggregation ."
              ::= { lldpNeighborInfoEntry 24 } 
              
          lldpNeighborLinkAggregationEnabled OBJECT-TYPE
            	SYNTAX  INTEGER {
	      							disable(0), 						--disable
	      							enable(1)								--enable
	      							}
              MAX-ACCESS  read-only
              STATUS  current
              DESCRIPTION
                      "Displays the enabled state of the link aggregation ."
              ::= { lldpNeighborInfoEntry 25 } 
              
          lldpNeighborAggregationPortId OBJECT-TYPE
            	SYNTAX  INTEGER
              MAX-ACCESS  read-only
              STATUS  current
              DESCRIPTION
                      "Displays the aggregation port id ."
              ::= { lldpNeighborInfoEntry 26 } 
              
          lldpNeighborPowerPortClass OBJECT-TYPE
            	SYNTAX  OCTET STRING (SIZE (0..255)) 
              MAX-ACCESS  read-only
              STATUS  current
              DESCRIPTION
                      "Displays the power port class."
              ::= { lldpNeighborInfoEntry 27 } 
              
          lldpNeighborPsePowerSupported OBJECT-TYPE
            	SYNTAX  INTEGER {
	      							disable(0), 						--disable
	      							enable(1)								--enable
	      							}
              MAX-ACCESS  read-only
              STATUS  current
              DESCRIPTION
                      "Displays the supported state of the PSE power ."
              ::= { lldpNeighborInfoEntry 28 }
              
          lldpNeighborPsePowerEnabled OBJECT-TYPE
            	SYNTAX  INTEGER {
	      							disable(0), 						--disable
	      							enable(1)								--enable
	      							}
              MAX-ACCESS  read-only
              STATUS  current
              DESCRIPTION
                      "Displays the enabled state of the PSE power."
              ::= { lldpNeighborInfoEntry 29 } 
              
          lldpNeighborPsePairsControlAbility OBJECT-TYPE
            	SYNTAX  INTEGER {
	      							disable(0), 						--disable
	      							enable(1)								--enable
	      							}
              MAX-ACCESS  read-only
              STATUS  current
              DESCRIPTION
                      "Displays the enabled state of the PSE pairs control."
              ::= { lldpNeighborInfoEntry 30 } 
              
          lldpNeighborMaximumFrameSize OBJECT-TYPE
            	SYNTAX  INTEGER 
              MAX-ACCESS  read-only
              STATUS  current
              DESCRIPTION
                      "Displays the size of the maximum frame."
              ::= { lldpNeighborInfoEntry 31 } 
	 END
