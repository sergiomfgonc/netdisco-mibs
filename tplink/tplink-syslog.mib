TPLINK-SYSLOG-MIB DEFINITIONS ::= BEGIN
IMPORTS
	TEXTUAL-CONVENTION
		FROM SNMPv2-TC
	MODULE-IDENTITY,OBJECT-TYPE,IpAddress
		FROM SNMPv2-SMI          
	tplinkMgmt	          
		FROM TPLINK-MIB;
tplinkSyslogMIB MODULE-IDENTITY
    LAST-UPDATED  "201211290000Z"
    ORGANIZATION  "TP-LINK"
    CONTACT-INFO  "www.tplink.com"
    DESCRIPTION
         "This MIB module contain a collection of managed objects
          that apply to network devices with Syslog function."
    REVISION    "201211290000Z"
    DESCRIPTION
        "Initial version of this MIB module."
    ::= { tplinkMgmt 24 }

tplinkSyslogMIBObjects	OBJECT IDENTIFIER ::= {tplinkSyslogMIB 1}
tplinkSyslogNotifications	OBJECT IDENTIFIER ::= {tplinkSyslogMIB 2}

MessageLevelType ::= TEXTUAL-CONVENTION
	STATUS current
	DESCRIPTION
		"Specify severity level of message."
	SYNTAX INTEGER
	{
		emergency(0),
		alert(1),
		critical(2),
		error(3),
		warning(4),
		notice(5),
		informational(6),
		debug(7)
	}        
  



tpSyslogBuffer OBJECT IDENTIFIER	::= { tplinkSyslogMIBObjects 1 } 

tpSyslogBufferSeverity OBJECT-TYPE 
	SYNTAX  MessageLevelType
	MAX-ACCESS  read-write
	STATUS  current
	DESCRIPTION
		"Select the severity of information to be stored to System Log Buffer."
	::= { tpSyslogBuffer 1 } 
		
tpSyslogBufferState OBJECT-TYPE 
	SYNTAX  INTEGER{
		disable(0), 						--disable
		enable(1)							--enable
	}
	MAX-ACCESS  read-write
	STATUS  current
	DESCRIPTION
		"Select Enable/Disable System Log Buffer on the Switch."
	::= { tpSyslogBuffer 2 }    

tpSyslogConsole OBJECT IDENTIFIER	::= { tplinkSyslogMIBObjects 2 } 

tpSyslogConsoleSeverity OBJECT-TYPE 
	SYNTAX  MessageLevelType
	MAX-ACCESS  read-write
	STATUS  current
	DESCRIPTION
		"Select the severity of information to be stored to System Log Console."
	::= { tpSyslogConsole 1 } 
		
tpSyslogConsoleState OBJECT-TYPE 
	SYNTAX  INTEGER{
		disable(0), 						--disable
		enable(1)							--enable
	}
	MAX-ACCESS  read-write
	STATUS  current
	DESCRIPTION
		"Select Enable/Disable System Log Console on the Switch."
	::= { tpSyslogConsole 2 }
	
tpSyslogFlash OBJECT IDENTIFIER ::= { tplinkSyslogMIBObjects 3 }        

tpSyslogFlashSeverity OBJECT-TYPE 
	SYNTAX  MessageLevelType
	MAX-ACCESS  read-write
	STATUS  current
	DESCRIPTION
		"Select the severity of information to be stored to System Log Flash."
	::= { tpSyslogFlash 1 } 
		
tpSyslogFlashState OBJECT-TYPE 
	SYNTAX  INTEGER{
		disable(0), 						--disable
		enable(1)							--enable
	}
	MAX-ACCESS  read-write
	STATUS  current
	DESCRIPTION
		"Select Enable/Disable System Log Flash on the Switch."
	::= { tpSyslogFlash 2 }    		

tpSyslogFlashSyncFrequency OBJECT-TYPE 
	SYNTAX  INTEGER(0..48)
	MAX-ACCESS  read-write
	STATUS  current
	DESCRIPTION
		"Specify the frequency of information to be synchronized to System Log Flash."
	::= { tpSyslogFlash 3 } 

tpSyslogMonitor OBJECT IDENTIFIER	::= { tplinkSyslogMIBObjects 4 } 

tpSyslogMonitorSeverity OBJECT-TYPE 
	SYNTAX  MessageLevelType
	MAX-ACCESS  read-write
	STATUS  current
	DESCRIPTION
		"Select the severity of information to be stored to System Log Monitor."
	::= { tpSyslogMonitor 1 } 
		
tpSyslogMonitorState OBJECT-TYPE 
	SYNTAX  INTEGER{
		disable(0), 						--disable
		enable(1)							--enable
	}
	MAX-ACCESS  read-write
	STATUS  current
	DESCRIPTION
		"Select Enable/Disable System Log Monitor on the Switch."
	::= { tpSyslogMonitor 2 }
	
tpSyslogHostTable OBJECT-TYPE
	SYNTAX  SEQUENCE OF TPSyslogHostEntry
	MAX-ACCESS  not-accessible
	STATUS  current
	DESCRIPTION
		"This table contain System Log Host information."
	::= { tplinkSyslogMIBObjects 5 }
 
	     
tpSyslogHostEntry OBJECT-TYPE
	SYNTAX TPSyslogHostEntry
	MAX-ACCESS  not-accessible
	STATUS  current
	DESCRIPTION
		"Configuration of System Log Host."  
	INDEX  { tpSyslogHostIndex }
	::= { tpSyslogHostTable 1 }
	           
TPSyslogHostEntry ::=
	SEQUENCE {
		tpSyslogHostIndex
			INTEGER,    
		tpSyslogHostIPAddress
			IpAddress,
		tpSyslogHostSeverity
			MessageLevelType,
		tpSyslogHostState
			INTEGER      
	}
        	    
tpSyslogHostIndex OBJECT-TYPE
	SYNTAX  INTEGER (1..4)
	MAX-ACCESS  read-only
	STATUS  current
	DESCRIPTION
		"The index of System Log Host entry ,and is unique."
	::= { tpSyslogHostEntry 1 }            
	        
tpSyslogHostIPAddress OBJECT-TYPE
	SYNTAX  IpAddress
	MAX-ACCESS  read-write
	STATUS  current
	DESCRIPTION
		"Specifies the IP address of the System Log Host."
	::= { tpSyslogHostEntry 2 }
	    
tpSyslogHostSeverity OBJECT-TYPE 
	SYNTAX  MessageLevelType
	MAX-ACCESS  read-write
	STATUS  current
	DESCRIPTION
		"Select the severity of information to be stored to System Log Host."
	::= { tpSyslogHostEntry 3 } 
		
tpSyslogHostState OBJECT-TYPE 
	SYNTAX  INTEGER{
		disable(0), 						--disable
		enable(1)							--enable
	}
	MAX-ACCESS  read-write
	STATUS  current
	DESCRIPTION
		"Select Enable/Disable System Log Host on the Switch."
	::= { tpSyslogHostEntry 4 }    
		
END
