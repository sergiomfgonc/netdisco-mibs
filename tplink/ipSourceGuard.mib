TLSG5412F-IP-SOURCE-GUARD-MIB DEFINITIONS ::= BEGIN

         IMPORTS
            OBJECT-TYPE
          	  	         	FROM SNMPv2-SMI
            ipSourceGuard	          
          	  	          FROM TLSG5412F-NET-SECURITY-MIB; 
          	  	          
			 	ipSourceGuardConfig  	OBJECT IDENTIFIER ::= {ipSourceGuard 1}
 
        -- the ip filter config       
        
         ipSourceGuardConfigTable OBJECT-TYPE
            SYNTAX  SEQUENCE OF IPFILTERCONFIGENTRY
            MAX-ACCESS  not-accessible
            STATUS  current
            DESCRIPTION
                    "A list of ip source guard config entries.
                     Here you can configure the IP Source Guard feature."
            ::= { ipSourceGuardConfig 1 }

        ipSourceGuardConfigEntry OBJECT-TYPE
            SYNTAX  IPFILTERCONFIGENTRY
            MAX-ACCESS  not-accessible
            STATUS  current
            DESCRIPTION
                    "An entry contains of the information of ip source guard config."
            INDEX   { ipSourceGuardConfigPort }
            ::= { ipSourceGuardConfigTable 1 }
    
        IPFILTERCONFIGENTRY ::=
            SEQUENCE {
								ipSourceGuardConfigPort
										INTEGER, 
								ipSourceGuardConfigType
										INTEGER,
								ipSourceGuardConfigPortLag
										OCTET STRING (SIZE (1..255)) 
            }
            
        ipSourceGuardConfigPort OBJECT-TYPE
            SYNTAX  INTEGER  
            MAX-ACCESS  read-only
            STATUS  current
            DESCRIPTION
                    "port number"
            ::= { ipSourceGuardConfigEntry 1 }
        
        ipSourceGuardConfigType OBJECT-TYPE
            SYNTAX  INTEGER{
	      		disable(0), 						
	      		sip(1),
	      		sip-mac(2)		
	      		}
            MAX-ACCESS  read-write
            STATUS  current
            DESCRIPTION
                    "Select Security Type for the port.
                     0. disable: Select this option to disable the IP Source Guard feature for the port.
                     1. SIP: Only the packets with its source IP address and port number matched 
                            to the IP-MAC binding rules can be processed. 
                     2. SIP+MAC: Only the packets with its source IP address, 
                                source MAC address and port number matched to the IP-MAC binding rules can be processed."
            ::= { ipSourceGuardConfigEntry 2 }    
            
        ipSourceGuardConfigPortLag OBJECT-TYPE
            SYNTAX  OCTET STRING (SIZE (1..255))  
            MAX-ACCESS  read-only
            STATUS  current
            DESCRIPTION
                    "the lag the port belong to"
            ::= { ipSourceGuardConfigEntry 3 }     
  			
END
