TLSG5412F-SYSTEMINFO-MIB DEFINITIONS ::= BEGIN

          IMPORTS
              TimeStamp          	 
  					FROM SNMPv2-TC
              OBJECT-TYPE
          	  	         	FROM SNMPv2-SMI
              sysConfig	          
          	  	          	FROM TLSG5412F-SYSTEM-MIB;
      	
      	      sysInfo		OBJECT IDENTIFIER ::= {sysConfig 1}
      	      
      	      
      	  sysInfoDescr OBJECT-TYPE
              SYNTAX  OCTET STRING (SIZE (0..255))
              MAX-ACCESS  read-only
              STATUS  current
              DESCRIPTION
                      "A textual description of the entity.  This value
                      should include the full name and version
                      identification of the system's hardware type,
                      software operating-system, and networking
                      software.  It is current that this only contain
                      printable ASCII characters."
              ::= { sysInfo 1 }
              
          sysInfoName OBJECT-TYPE
              SYNTAX  OCTET STRING (SIZE (0..255))
              MAX-ACCESS  read-write
              STATUS  current
              DESCRIPTION
                      "An administratively-assigned name for this
                      managed node.  By convention, this is the node's
                      fully-qualified domain name.range:32 byte."
              ::= { sysInfo 2 }
              
          sysInfoLocation OBJECT-TYPE
              SYNTAX  OCTET STRING (SIZE (0..255))
              MAX-ACCESS  read-write
              STATUS  current
              DESCRIPTION
                      "The physical location of this node (e.g.,
                      `telephone closet, 3rd floor'),range:32 byte."
              ::= { sysInfo 3 }   
          
	sysInfoContact OBJECT-TYPE
              SYNTAX  OCTET STRING (SIZE (0..255))
              MAX-ACCESS  read-write
              STATUS  current
              DESCRIPTION
                      "The textual identification of the contact person
                      for this managed node, together with information
                      on how to contact this person.range:32 byte."
              ::= { sysInfo 4 }
					
	  sysInfoHwVersion OBJECT-TYPE	
	      SYNTAX  OCTET STRING (SIZE (0..255))
              MAX-ACCESS  read-only
              STATUS  current
              DESCRIPTION
                      "The hardware version of the product."
              ::= { sysInfo 5 }
	  			
	  sysInfoSwVersion OBJECT-TYPE	
	      SYNTAX  OCTET STRING (SIZE (0..255))
              MAX-ACCESS  read-only
              STATUS  current
              DESCRIPTION
                      "The software version of the product."
              ::= { sysInfo 6 }
              
          sysInfoMacAddr	OBJECT-TYPE
              SYNTAX  OCTET STRING (SIZE (0..255))
              MAX-ACCESS  read-only
              STATUS  current
              DESCRIPTION
                      "The MAC address of the product."
              ::= { sysInfo 7 }
              
              
          sysInfoUpTime OBJECT-TYPE
              SYNTAX  TimeStamp
              MAX-ACCESS  read-only
              STATUS  current
              DESCRIPTION
                      "The time (in hundredths of a second) since the
                      network management portion of the system was last
                      re-initialized."
              ::= { sysInfo 8 }
      	
          END
