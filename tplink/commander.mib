TLSG5412F-COMMANDER-MIB DEFINITIONS ::= BEGIN
		IMPORTS
		  OBJECT-TYPE
			  	         	FROM SNMPv2-SMI
			DisplayString 
										FROM SNMPv2-TC
			IpAddress
										FROM RFC1155-SMI 										        	  	         	
			clusterManage
										FROM TLSG5412F-CLUSTER-MIB;
																
	    clusterConfig	OBJECT IDENTIFIER ::= {clusterManage 2}
	    commanderConfig	OBJECT IDENTIFIER ::=	{clusterConfig 4}
	    
   		clusterName OBJECT-TYPE
   			SYNTAX				DisplayString(SIZE(1..16))
   			MAX-ACCESS		read-write
   			STATUS				current
   			DESCRIPTION		
   			"This object indicates the name of the cluster if the role of the switch
   			is commander. The minimum length is 1, maximum length is 16. The cluster name
   			can not contain any of the char ,&<>\."
   			::=	{clusterConfig 1}
   				
   		clusterHoldTime	OBJECT-TYPE
   			SYNTAX				INTEGER(1..255)
   			MAX-ACCESS		read-write
   			STATUS				current
   			DESCRIPTION		
   			"This object indicates the time that the cluster information will keep
   			in the commander switch. The minimum value is 1, maximum value is 255."
   			::=	{clusterConfig 2}
   		
   		clusterIntervalTime OBJECT-TYPE
   			SYNTAX				INTEGER(1..255)
   			MAX-ACCESS		read-write
   			STATUS				current
   			DESCRIPTION		
   			"This object indicates the interval time of the switch in second to periodical
    		send out handshake packet. The minimum value is 1, maximum value is 255."
   			::=	{clusterConfig 3}
   		
   		commanderClusterName OBJECT-TYPE
   			SYNTAX				DisplayString(SIZE(1..16))
   			MAX-ACCESS		read-write
   			STATUS				current
   			DESCRIPTION		
   			"This object use to set the cluster name when building the cluster.
				The minimum length is 1, maximum length is 16. The cluster name
				can not contain any of the char ,&<>\."
   			::=	{commanderConfig 1}
   			
   		clusterIp				OBJECT-TYPE
   			SYNTAX				IpAddress
   			MAX-ACCESS		read-write
   			STATUS				current
   			DESCRIPTION		
   			"This object use to set the cluster ip pool when building the cluster."
   			::=	{commanderConfig 2}
   		
   		clusterIpMask		OBJECT-TYPE
   			SYNTAX				IpAddress
   			MAX-ACCESS		read-write
   			STATUS				current
   			DESCRIPTION		
   			"This object use to set the cluster ip mask when building the cluster."
   			::=	{commanderConfig 3}
   			
   		clusterCommit		OBJECT-TYPE
   			SYNTAX				
   				INTEGER
   				{
   					commit(1)
   				}
   			MAX-ACCESS		read-write
   			STATUS				current
   			DESCRIPTION		
   			"This object use to commit the data to build the cluster."
   			::=	{commanderConfig 4}	    
END
