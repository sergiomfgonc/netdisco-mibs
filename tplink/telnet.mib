TLSG3424-TELNET-MIB DEFINITIONS ::= BEGIN

		IMPORTS
			OBJECT-TYPE,MODULE-IDENTITY
				FROM SNMPv2-SMI
			accessSecurity	          
          	  	FROM TLSG3424-SYSTEM-MIB;

		telnet	OBJECT IDENTIFIER ::= {accessSecurity 4}

		telnetConfig	OBJECT-TYPE
			SYNTAX  INTEGER{
					disable(0),
					enable(1)
					}
			MAX-ACCESS  read-write
			STATUS  current
			DESCRIPTION
					"0. disable
					1. enable"
			::= { telnet 1 }


		END
