TLSG3424-PORTLOOPBACKDETECTION-MIB DEFINITIONS ::= BEGIN
		IMPORTS
		  OBJECT-TYPE,MODULE-IDENTITY
			  	         	FROM SNMPv2-SMI     	  	         	
			l2PortManage
										FROM TLSG3424-L2SWITCH-MIB;
										
			l2LoopBackDetection MODULE-IDENTITY  
	    LAST-UPDATED    "200908270000Z"
	    ORGANIZATION    "TPLINK"
	    CONTACT-INFO		"www.tplink.com.cn"
	    DESCRIPTION			"The config of the port mirror."
	    REVISION        "200908270000Z"
	    DESCRIPTION			"Initial version of this MIB module."
	    ::= { l2PortManage 5 }
	    
	    loopbackDetectionEnable OBJECT-TYPE
         			SYNTAX  INTEGER{
	      							disable(0), 						--disable
	      							enable(1)								--enable
	      							}
              MAX-ACCESS  read-write
              STATUS  current
              DESCRIPTION
                      "Select Enable/Disable LOOPBACK detection function globally on the Switch.
                      0. disable 
                      1. enable"
              ::= { l2LoopBackDetection 1 } 
	    
	    loopbackDetectionInterval OBJECT-TYPE
         			SYNTAX  INTEGER(1..1000) 
              MAX-ACCESS  read-write
              STATUS  current
              DESCRIPTION
                      "The interval time of lookback detection"
              ::= { l2LoopBackDetection 2 }  
              
       loopbackDetectionRecoveryTime OBJECT-TYPE
         			SYNTAX  INTEGER(1..100) 
              MAX-ACCESS  read-write
              STATUS  current
              DESCRIPTION
                      "The recovery time of lookback detection"
              ::= { l2LoopBackDetection 3 }
			    
																										          	  	          
	   		loopbackDetectionCtrlTable OBJECT-TYPE
              SYNTAX  SEQUENCE OF PORTISOLATIONCTRLENTRY
              MAX-ACCESS  not-accessible
              STATUS  current
              DESCRIPTION
                      "A list of port loopback detection."
              ::= { l2LoopBackDetection 4 }
              
              loopbackStatusChange NOTIFICATION-TYPE
              STATUS  current
              DESCRIPTION
                      "When loopbackDetection is enabled ,A loopback detection notification is sent while port loop status is changed."
              ::= { l2LoopBackDetection 5 }
              
         loopbackDetectionCtrlEntry OBJECT-TYPE
              SYNTAX  PORTISOLATIONCTRLENTRY
              MAX-ACCESS  not-accessible
              STATUS  current
              DESCRIPTION
                      "The entry of the port loopback detection list ."
              INDEX   { loopbackDetectionPortId }
              ::= { loopbackDetectionCtrlTable 1 }
              
              
        PORTISOLATIONCTRLENTRY ::=
              SEQUENCE {
                  loopbackDetectionPortId
                      INTEGER, 
                  loopbackDetectionState
                  		INTEGER{
	      										disable(0), 					--Disable
	      										enable(1)						--Enable
	      											}, 
                  loopbackDetectionProcessMode
                  		INTEGER{
	      										alert(0), 					--Alert
	      										portbased(1)						--Portbased
	      											},
                  loopbackDetectionRecoverMode
                  		INTEGER{
	      										auto(0), 					--Auto
	      										manual(1)						--Manual
	      											},
                  loopbackDetectionLoopState
                  		OCTET STRING (SIZE (0..255)),
                  loopbackDetectionBlockState
                  		OCTET STRING (SIZE (0..255)),
                  loopbackDetectionLagState
                  		OCTET STRING (SIZE (0..255)),
                  loopbackDetectionRecoverPort
                  		INTEGER
              }
              
         loopbackDetectionPortId  OBJECT-TYPE
			     SYNTAX  INTEGER  
			      MAX-ACCESS  read-only
			      STATUS  current
			      DESCRIPTION
			              "The port id."
			      ::= { loopbackDetectionCtrlEntry 1 }
			      
			   loopbackDetectionState  OBJECT-TYPE
			     SYNTAX  INTEGER{
	      										disable(0), 					--Disable
	      										enable(1)						--Enable
	      											}   
			      MAX-ACCESS  read-write
			      STATUS  current
			      DESCRIPTION
			              "The state of the port."
			      ::= { loopbackDetectionCtrlEntry 2 }
			      
			   loopbackDetectionProcessMode  OBJECT-TYPE
			     SYNTAX  INTEGER{
	      										alert(0), 					--Alert
	      										portbased(1)						--Portbased
	      											} 
			      MAX-ACCESS  read-write
			      STATUS  current
			      DESCRIPTION
			              "The process mode of the port."
			      ::= { loopbackDetectionCtrlEntry 3 }
			      
			   loopbackDetectionRecoverMode  OBJECT-TYPE
			     SYNTAX  INTEGER{
	      										auto(0), 					--Auto
	      										manual(1)						--Manual
	      											}  
			      MAX-ACCESS  read-write
			      STATUS  current
			      DESCRIPTION
			              "The recover mode of the port."
			      ::= { loopbackDetectionCtrlEntry 4 }
			      
			    loopbackDetectionLoopState  OBJECT-TYPE
			     SYNTAX  OCTET STRING (SIZE (0..255))  
			      MAX-ACCESS  read-only
			      STATUS  current
			      DESCRIPTION
			              "The loop state of the port."
			      ::= { loopbackDetectionCtrlEntry 5 }
			      
			    loopbackDetectionBlockState  OBJECT-TYPE
			     SYNTAX  OCTET STRING (SIZE (0..255))  
			      MAX-ACCESS  read-only
			      STATUS  current
			      DESCRIPTION
			              "The block state of the port."
			      ::= { loopbackDetectionCtrlEntry 6 }
			      
			    loopbackDetectionLagState  OBJECT-TYPE
			     SYNTAX  OCTET STRING (SIZE (0..255))  
			      MAX-ACCESS  read-only
			      STATUS  current
			      DESCRIPTION
			              "The LAG  of the port."
			      ::= { loopbackDetectionCtrlEntry 7 }
			      
			      
			    loopbackDetectionRecoverPort OBJECT-TYPE
			     SYNTAX  INTEGER 
			      MAX-ACCESS  read-write
			      STATUS  current
			      DESCRIPTION
			              "You can recover the block port with this."
			      ::= { loopbackDetectionCtrlEntry 8 }

			      
END
