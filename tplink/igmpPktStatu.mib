-- Performance multicast pkt statistic config
-- modify history: not change
--    

TLSG5412F-IGMP-PKT-STAT-MIB DEFINITIONS ::= BEGIN

          IMPORTS
              OBJECT-TYPE,MODULE-IDENTITY
          	  	         	FROM SNMPv2-SMI
              	igmpPacketStatistic	          
          	  	          	FROM  TLSG5412F-IGMP-MANAGE-MIB;
          	  	          	
          	  	          	        	
       		
       	igmpPktStat MODULE-IDENTITY  
			    LAST-UPDATED    "200812160000Z"
			    ORGANIZATION    "TPLINK"
			    CONTACT-INFO		"www.tplink.com.cn"
			    DESCRIPTION
			             "Here you can view multicast packet statistics over each port 
			             of the switch, which facilitates you monitor the IGMP packets
			             in the network."
			    REVISION        "200909010000Z"
			    DESCRIPTION
					"Initial version of this MIB module."
			    ::= { igmpPacketStatistic 1 }      	      
      	   

          
          
          igmpPktStatTable OBJECT-TYPE
              SYNTAX  SEQUENCE OF MULTIPKTSTATENTRY
              MAX-ACCESS  not-accessible
              STATUS  current
              DESCRIPTION
                      "A list of  multicast statistic Table."
              ::= { igmpPktStat 1 }

          igmpPktStatEntry OBJECT-TYPE
              SYNTAX  MULTIPKTSTATENTRY
              MAX-ACCESS  not-accessible
              STATUS  current
              DESCRIPTION
                      "An entry contains of multicast packet statistics over each port."
              INDEX   { igmpPktStatPortNumber }
              ::= { igmpPktStatTable 1 }
      
          MULTIPKTSTATENTRY ::=
              SEQUENCE {
                 	igmpPktStatPortNumber
              				INTEGER,
                  igmpQueryPktStat
                      INTEGER,
                 	igmpReportV1PktStat
              				INTEGER,
                  igmpReportV2PktStat
                      INTEGER,
                  igmpReportV3PktStat
                      INTEGER,
                 	igmpLeavePktStat
              				INTEGER,
                  igmpErrorPktStat
                      INTEGER
              }
              
              
            igmpPktStatPortNumber OBJECT-TYPE
            	 SYNTAX  INTEGER
              MAX-ACCESS  read-only
              STATUS  current
              DESCRIPTION
                      "Displays the port number of the switch."
              ::= { igmpPktStatEntry 1 }
                 
            igmpQueryPktStat OBJECT-TYPE
            	 SYNTAX  INTEGER
              MAX-ACCESS  read-only
              STATUS  current
              DESCRIPTION
                      "Displays the number of query packets the port received."
              ::= { igmpPktStatEntry 2 }
           
        	igmpReportV1PktStat OBJECT-TYPE
            	 SYNTAX  INTEGER
              MAX-ACCESS  read-only
              STATUS  current
              DESCRIPTION
                      "Displays the number of IGMPv1 report packets the port received."
              ::= { igmpPktStatEntry 3 }
                 
          igmpReportV2PktStat OBJECT-TYPE
            	 SYNTAX  INTEGER
              MAX-ACCESS  read-only
              STATUS  current
              DESCRIPTION
                      "Displays the number of IGMPv2 report packets the port received."
              ::= { igmpPktStatEntry 4 }
              
          igmpReportV3PktStat OBJECT-TYPE
            	 SYNTAX  INTEGER
              MAX-ACCESS  read-only
              STATUS  current
              DESCRIPTION
                      "Displays the number of IGMPv3 report packets the port received."
              ::= { igmpPktStatEntry 5 }
                 
           igmpLeavePktStat OBJECT-TYPE
            	 SYNTAX  INTEGER
              MAX-ACCESS  read-only
              STATUS  current
              DESCRIPTION
                      "Displays the number of leave packets the port received."
              ::= { igmpPktStatEntry 6 }
              
            igmpErrorPktStat OBJECT-TYPE
            	 SYNTAX  INTEGER
              MAX-ACCESS  read-only
              STATUS  current
              DESCRIPTION
                      "Displays the number of error packets the port received."
              ::= { igmpPktStatEntry 7 }
       
		       igmpPktStatClear OBJECT-TYPE
		            	 SYNTAX INTEGER
									   				{
									   					commit(1)
									   				}
		              MAX-ACCESS  read-write
		              STATUS  current
		              DESCRIPTION
		                      "igmp packet statistic clear."
		              ::= { igmpPktStat 2 }
       
          END
