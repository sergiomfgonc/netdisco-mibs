TLSG5412F-BAND-WIDTH-MIB DEFINITIONS ::= BEGIN

         IMPORTS
            OBJECT-TYPE
          	  	         	FROM SNMPv2-SMI
            bandWidth	          
          	  	          FROM  TLSG5412F-SERVICE-QUALITY-MIB; 
          	  	          
			 	rateLimit  				OBJECT IDENTIFIER ::= {bandWidth 1}
		stormControlNew		OBJECT IDENTIFIER ::= {bandWidth 3}
              
        -- the rate limit    
        
         rateLimitTable OBJECT-TYPE
            SYNTAX  SEQUENCE OF RATELIMITENTRY
            MAX-ACCESS  not-accessible
            STATUS  current
            DESCRIPTION
                    "A list of rate limit entries.
                     Here you can configure the traffic rate on each port."
            ::= { rateLimit 1 }

        rateLimitEntry OBJECT-TYPE
            SYNTAX  RATELIMITENTRY
            MAX-ACCESS  not-accessible
            STATUS  current
            DESCRIPTION
                    "An entry contains of the information of rate limit."
            INDEX   { rateLimitPort }
            ::= { rateLimitTable 1 }
    
        RATELIMITENTRY ::=
            SEQUENCE {
								rateLimitPort
										INTEGER, 
								rateLimitIngressRate
										INTEGER,
								rateLimitEgressRate
										INTEGER,
								rateLimitPortLag
										OCTET STRING (SIZE (1..255))	
            }
            
        rateLimitPort OBJECT-TYPE
            SYNTAX  INTEGER  
            MAX-ACCESS  read-only
            STATUS  current
            DESCRIPTION
                    "The port number of the Switch."
            ::= { rateLimitEntry 1 }
        
        rateLimitIngressRate OBJECT-TYPE
            SYNTAX  INTEGER(1..1024000)
            MAX-ACCESS  read-write
            STATUS  current
            DESCRIPTION
                    "Set the bandwidth for receiving packets on the port."
            ::= { rateLimitEntry 2 }
       
       rateLimitEgressRate OBJECT-TYPE
            SYNTAX  INTEGER(1..1024000)
            MAX-ACCESS  read-write
            STATUS  current
            DESCRIPTION
                    "Set the bandwidth for sending packets on the port."
            ::= { rateLimitEntry 3 }
        
        rateLimitPortLag OBJECT-TYPE
            SYNTAX  OCTET STRING (SIZE (1..255))  
            MAX-ACCESS  read-only
            STATUS  current
            DESCRIPTION
                    "The LAG number which the port belongs to."
            ::= { rateLimitEntry 4 }    
      
       -- the storm control
        
         stormControlTable OBJECT-TYPE
            SYNTAX  SEQUENCE OF STORMCONTROLENTRY
            MAX-ACCESS  not-accessible
            STATUS  current
            DESCRIPTION
                    "A list of storm control entries.
                     Here you can configure the bandwidth for forwarding packets."
            ::= { stormControl 1 }

        stormControlEntry OBJECT-TYPE
            SYNTAX  STORMCONTROLENTRY
            MAX-ACCESS  not-accessible
            STATUS  current
            DESCRIPTION
                    "An entry contains of the information of storm control."
            INDEX   { stormControlPort }
            ::= { stormControlTable 1 }
    
        STORMCONTROLENTRY ::=
            SEQUENCE {
								stormControlPort
										INTEGER, 
								stormControlBroadCastRate
										INTEGER,
								stormControlMultiCastRate
										INTEGER,
								stormControlULRate
										INTEGER,
								stormControlPortLag
										OCTET STRING (SIZE (1..255))  			
            }
            
        stormControlPort OBJECT-TYPE
            SYNTAX  INTEGER  
            MAX-ACCESS  read-only
            STATUS  current
            DESCRIPTION
                    "The port number of the Switch."
            ::= { stormControlEntry 1 }
        
        stormControlBroadCastRate OBJECT-TYPE
            SYNTAX  INTEGER{
	      		bc-128Kbps(1), 						
	      		bc-256Kbps(2),
	      		bc-512Kbps(3),
	      		bc-1Mbps(4),
	      		bc-2Mbps(5),
	      		bc-4Mbps(6),
	      		bc-5Mbps(7),		
	      		bc-10Mbps(8),
	      		bc-20Mbps(9),
	      		bc-40Mbps(10),
	      		bc-50Mbps(11),
	      		bc-disable(0)					
	      		}
            MAX-ACCESS  read-write
            STATUS  current
            DESCRIPTION
                    "1. 128Kbps
                     2. 256Kbps
                     3. 512Kbps
                     4. 1Mbps
                     5. 2Mbps
                     6. 4Mbps
                     7. 5Mbps
                     8. 10Mbps
                     9.	20Mbps
                     10.	40Mbps
                     11.50Mbps
                     0.disable
                     Select the bandwidth for receiving broadcast packets on the port. 
                     The packet traffic exceeding the bandwidth will be discarded. 
                     Select Disable to disable the storm control function for the port."
            ::= { stormControlEntry 2 }
       
       stormControlMultiCastRate OBJECT-TYPE
            SYNTAX  INTEGER{
	      		mc-128Kbps(1), 						
	      		mc-256Kbps(2),
	      		mc-512Kbps(3),
	      		mc-1Mbps(4),
	      		mc-2Mbps(5),
	      		mc-4Mbps(6),
	      		mc-5Mbps(7),		
	      		mc-10Mbps(8),
	      		mc-20Mbps(9),
	      		mc-40Mbps(10),
	      		mc-50Mbps(11),
	      		mc-disable(0)					
	      		}
            MAX-ACCESS  read-write
            STATUS  current
            DESCRIPTION
                    "1. 128Kbps
                     2. 256Kbps
                     3. 512Kbps
                     4. 1Mbps
                     5. 2Mbps
                     6. 4Mbps
                     7. 5Mbps
                     8. 10Mbps
                     9.	20Mbps
                     10.	40Mbps
                     11.50Mbps
                     0.disable
                     Select the bandwidth for receiving multicast packets on the port. 
                     The packet traffic exceeding the bandwidth will be discarded. 
                     Select Disable to disable the storm control function for the port."
            ::= { stormControlEntry 3 }
            
     stormControlULRate OBJECT-TYPE
            SYNTAX  INTEGER{
	      		ul-128Kbps(1), 						
	      		ul-256Kbps(2),
	      		ul-512Kbps(3),
	      		ul-1Mbps(4),
	      		ul-2Mbps(5),
	      		ul-4Mbps(6),
	      		ul-5Mbps(7),		
	      		ul-10Mbps(8),
	      		ul-20Mbps(9),
	      		ul-40Mbps(10),
	      		ul-50Mbps(11),
	      		ul-disable(0)					
	      		}
            MAX-ACCESS  read-write
            STATUS  current
            DESCRIPTION
                    "1. 128Kbps
                     2. 256Kbps
                     3. 512Kbps
                     4. 1Mbps
                     5. 2Mbps
                     6. 4Mbps
                     7. 5Mbps
                     8. 10Mbps
                     9.	20Mbps
                     10.	40Mbps
                     11.50Mbps
                     0.disable
                     Select the bandwidth for receiving UL-Frame on the port. 
                     The packet traffic exceeding the bandwidth will be discarded. 
                     Select Disable to disable the storm control function for the port. "
            ::= { stormControlEntry 4 }
            
     stormControlPortLag OBJECT-TYPE
            SYNTAX  OCTET STRING (SIZE (1..255))  
            MAX-ACCESS  read-only
            STATUS  current
            DESCRIPTION
                    "The LAG number which the port belongs to. "
            ::= { stormControlEntry 5 }
			
			
			
	  -- the storm control new version
        
     stormControlNewTable OBJECT-TYPE
            SYNTAX  SEQUENCE OF STORMCONTROLENTRYNEW
            MAX-ACCESS  not-accessible
            STATUS  current
            DESCRIPTION
                    "A list of storm control entries.
                     Here you can configure the bandwidth for forwarding packets."
            ::= { stormControlNew 1 }

        stormControlEntryNew OBJECT-TYPE
            SYNTAX  STORMCONTROLENTRYNEW
            MAX-ACCESS  not-accessible
            STATUS  current
            DESCRIPTION
                    "An entry contains of the information of storm control."
            INDEX   { stormControlNewPort }
            ::= { stormControlNewTable 1 }
    
        STORMCONTROLENTRYNEW ::=
            SEQUENCE {
								stormControlNewPort
										INTEGER, 
								stormControlNewBoardCastEnable
										INTEGER,
								stormControlNewMultiCastEnable
										INTEGER,
								stormControlNewULEnable
										INTEGER, 
								stormControlNewRate
										INTEGER,		
								stormControlNewPortLag
										OCTET STRING (SIZE (1..255))  			
            }
            
        stormControlNewPort OBJECT-TYPE
            SYNTAX  INTEGER  
            MAX-ACCESS  read-only
            STATUS  current
            DESCRIPTION
                    "The port number of the Switch."
            ::= { stormControlEntryNew 1 }
        
        stormControlNewBoardCastEnable OBJECT-TYPE
            SYNTAX  INTEGER{
	      		enable(1),
	      		disable(0)					
	      		}
            MAX-ACCESS  read-write
            STATUS  current
            DESCRIPTION
                    "1.enable
                     0.disable
                     Select the bandwidth for receiving broadcast packets on the port. 
                     The packet traffic exceeding the bandwidth will be discarded. 
                     Select Disable to disable the storm control function for the port."
            ::= { stormControlEntryNew 2 }
       
        stormControlNewMultiCastEnable OBJECT-TYPE
            SYNTAX  INTEGER{
	      		enable(1),
				disable(0)
	      		}
            MAX-ACCESS  read-write
            STATUS  current
            DESCRIPTION
                    "1. enable
                     0.disable
                     Select the bandwidth for receiving multicast packets on the port. 
                     The packet traffic exceeding the bandwidth will be discarded. 
                     Select Disable to disable the storm control function for the port."
            ::= { stormControlEntryNew 3 }
            
        stormControlNewULEnable OBJECT-TYPE
            SYNTAX  INTEGER{
	      		enable(1),
				disable(0)					
	      		}
            MAX-ACCESS  read-write
            STATUS  current
            DESCRIPTION
                    "1. enable
                     0.disable
                     Select the bandwidth for receiving UL-Frame on the port. 
                     The packet traffic exceeding the bandwidth will be discarded. 
                     Select Disable to disable the storm control function for the port. "
            ::= { stormControlEntryNew 4 }
			
	 stormControlNewRate OBJECT-TYPE
            SYNTAX  INTEGER{
	      		ra-128Kbps(1), 						
	      		ra-256Kbps(2),
	      		ra-512Kbps(3),
	      		ra-1Mbps(4),
	      		ra-2Mbps(5),
	      		ra-4Mbps(6),
	      		ra-5Mbps(7),		
	      		ra-10Mbps(8),
	      		ra-20Mbps(9),
	      		ra-40Mbps(10),
	      		ra-50Mbps(11),
	      		ra-disable(0)					
	      		}
            MAX-ACCESS  read-write
            STATUS  current
            DESCRIPTION
                    "1. 128Kbps
                     2. 256Kbps
                     3. 512Kbps
                     4. 1Mbps
                     5. 2Mbps
                     6. 4Mbps
                     7. 5Mbps
                     8. 10Mbps
                     9.	20Mbps
                     10.	40Mbps
                     11.50Mbps
                     0.disable
                     Select the bandwidth for receiving UL-Frame on the port. 
                     The packet traffic exceeding the bandwidth will be discarded. 
                     Select Disable to disable the storm control function for the port. "
            ::= { stormControlEntryNew 5 }
        
            
     stormControlNewPortLag OBJECT-TYPE
            SYNTAX  OCTET STRING (SIZE (1..255))  
            MAX-ACCESS  read-only
            STATUS  current
            DESCRIPTION
                    "The LAG number which the port belongs to. "
            ::= { stormControlEntryNew 6 }
END
