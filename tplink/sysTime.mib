TLSG5412F-SYSTIME-MIB DEFINITIONS ::= BEGIN

          IMPORTS
              OBJECT-TYPE,  IpAddress 
          	  	         	FROM SNMPv2-SMI
              
              sysConfig	          
          	  	          	FROM TLSG5412F-SYSTEM-MIB;
      	
      	      sysTime		OBJECT IDENTIFIER ::= {sysConfig 3}
      
    
      	  
      	  sysTimeCurrentTime	   OBJECT-TYPE
      	       SYNTAX      OCTET STRING(SIZE (0..255)) 
	       MAX-ACCESS  read-only
	       STATUS      current
	       DESCRIPTION
	               "the date"
	       ::= { sysTime 1 }
	       
      	  sysTimeSource			OBJECT-TYPE
      	       SYNTAX      OCTET STRING(SIZE (0..255)) 
	       MAX-ACCESS  read-only
	       STATUS      current
	       DESCRIPTION
	               "the time source"
	       ::= { sysTime 2 }
	       
	  sysTimeMode			OBJECT-TYPE
      	       SYNTAX      OCTET STRING(SIZE (0..255)) 
	       MAX-ACCESS  read-only
	       STATUS      current
	       DESCRIPTION
	               "the time mode"
	       ::= { sysTime 3 }
      	  
      	  sysTimeManualTimeConfig		OBJECT IDENTIFIER ::= {sysTime 4}
      	  sysTimeGmtTimeConfig		OBJECT IDENTIFIER ::= {sysTime 5}
      	  dstConfig	    OBJECT IDENTIFIER ::= {sysTime 6}	
      	  --sysTimePcTimeConfig		OBJECT IDENTIFIER ::= {sysTime 6}

	       
	 sysTimeManualTimeEnable	 OBJECT-TYPE
	       SYNTAX      INTEGER{
	      		disable(0), 						--disable
	      		enable(1)						--enable
	      		}
	       MAX-ACCESS  read-write
	       STATUS      current
	       DESCRIPTION
	               "0.disable
	               	1.enable"
	       ::= { sysTimeManualTimeConfig 1 }
      	  
      	  sysTimeDate	 	OBJECT-TYPE
	       SYNTAX      OCTET STRING
	       MAX-ACCESS  read-write
	       STATUS      current
	       DESCRIPTION
	               "the data the set"
	       ::= { sysTimeManualTimeConfig 2 }
	       
	  sysTimeGmtTimeEnable	 OBJECT-TYPE
	       SYNTAX      INTEGER{
	      		disable(0), 						--disable
	      		enable(1)						--enable
	      		}
	       MAX-ACCESS  read-write
	       STATUS      current
	       DESCRIPTION
	               "0.disable
	               	1.enable"
	       ::= { sysTimeGmtTimeConfig 1 }	
	       
	   sysTimeGmtTimezone	 OBJECT-TYPE
	       SYNTAX      INTEGER{
							utc-1200(-1200),
							utc-1100(-1100), 
							utc-1000(-1000), 
							utc-0900(-900),
							utc-0800(-800),
							utc-0700(-700), 
							utc-0600(-600),
							utc-0500(-500),
							utc-0430(-450),
							utc-0400(-400),
							utc-0330(-350), 
							utc-0300(-300),
							utc-0200(-200),
							utc-0100(-100), 
							utc(0), 	  
							utc0100(100), 
							utc0200(200), 
							utc0300(300),
							utc0330(350),
							utc0400(400), 
							utc0430(450), 
							utc0500(500), 
							utc0530(550), 
							utc0545(575), 
							utc0600(600), 
							utc0630(650), 
							utc0700(700), 
							utc0800(800), 
							utc0900(900), 
							utc0930(950),
							utc1000(1000), 
							utc1100(1100), 
							utc1200(1200), 
							utc1300(1300)	      		
	      		}
	       MAX-ACCESS  read-write
	       STATUS      current
	       DESCRIPTION
	               "time zone select:
							utc-1200,	--International Date Line West
							utc-1100, 	--Coordinated Universal Time-11
							utc-1000, 	--Hawaii
							utc-0900, 	--Alaska
							utc-0800, 	--Pacific Time (US & Canada), Baja California
							utc-0700, 	--Mountain Time (US & Canada), Chihuahua, La Paz, Mazatlan, Arizona
							utc-0600, 	--Saskatchewan, Central America, Central Time (US & Canada), Guadalajara, 
										Mexico City, Monterrey
							utc-0500, 	--Eastern Time (US & Canada), Bogota, Lima, Quito, Indiana (East)
							utc-0430, 	--Caracas	
							utc-0400, 	--Atlantic Time (Canada), Cuiaba, Santiago, Asuncion, Georgetown, La Paz,
										Manaus, San Juan
							utc-0330, 	--Newfoundland
							utc-0300, 	--Buenos Aires, Salvador, Brasilia, Greenland, Montevideo, Cayenne, Fortaleza
							utc-0200, 	--Mid-Atlantic, Coordinated Universal Time-02
							utc-0100, 	--Azores, Cape Verde Is.
							utc, 		--Dublin, Edinburgh, Lisbon, London, Monrovia, Reykjavik, Casablanca, Coordinated 
										Universal Time
							utc0100, 	--Belgrade, Bratislava, Budapest, Ljubljana, Prague, Sarajevo, Skopje, Warsaw, 
										Zagreb, Tripoli, Windhoek, Brussels, Copenhagen, Madrid, Paris, West Central
										Africa, Amsterdam, Berlin, Bern, Rome, Stockholm, Vienna
							utc0200, 	--E. Europe, Cairo, Amman, Helsinki, Kyiv, Riga, Sofia, Tallinn, Vilnius, Athens, 
										Bucharest, Jerusalem, Beirut, Harare, Pretoria, Damascus, Istanbul, 
							utc0300, 	--Kuwait, Riyadh, Baghdad, Nairobi, Kaliningrad, Minsk
							utc0330, 	--Tehran
							utc0400, 	--Abu Dhabi, Muscat, Baku, Yerevan, Tbilisi, Port Louis, Moscow, St. Petersburg, 
										Volgograd
							utc0430, 	--Kabul
							utc0500, 	--Islamabad, Karachi, Tashkent
							utc0530, 	--Chennai, Kolkata, Mumbai, New Delhi, Sri Jayawardenepura
							utc0545, 	--Kathmandu
							utc0600, 	--Dhaka, Astana, Ekaterinburg
							utc0630, 	--Yangon (Rangoon)
							utc0700, 	--Novosibirsk, Bangkok, Hanoi, Jakarta
							utc0800, 	--Beijing, Chongqing, Hong Kong, Urumqi, Krasnoyarsk, Kuala Lumpur, Singapore, 
										Taipei, Ulaanbaatar, Perth
							utc0900, 	--Seoul, Irkutsk, Osaka, Sapporo, Tokyo
							utc0930, 	--Darwin, Adelaide
							utc1000, 	--Canberra, Melbourne, Sydney, Brisbane, Hobart, Guam, Port Moresby, Yakutsk
							utc1100, 	--Solomon Is., New Caledonia, Vladivostok
							utc1200, 	--Fiji, Magadan, Auckland, Wellington, Petropavlovsk-Kamchatsky, Coordinated 
										Universal Time+12
							utc1300, 	--Nuku'alofa, Samoa"
	       ::= { sysTimeGmtTimeConfig 2 }	
	       
	   sysTimeGmtNtpServer	OBJECT-TYPE
      	 	SYNTAX      IpAddress
	       MAX-ACCESS  read-write
	       STATUS      current
	       DESCRIPTION
	               "ip address of ntp server,for example: 133.100.9.2."
	       ::= { sysTimeGmtTimeConfig 3 }	
      	   
      	   sysTimeGmtBackupNtpServer	OBJECT-TYPE
      	 	SYNTAX      IpAddress
	       MAX-ACCESS  read-write
	       STATUS      current
	       DESCRIPTION
	               "ip address of ntp backup server,for example: 139.78.100.163."
	       ::= { sysTimeGmtTimeConfig 4 }	
	END
