TLSG5412F-PORTSECURITY-MIB DEFINITIONS ::= BEGIN
		IMPORTS
		  OBJECT-TYPE,MODULE-IDENTITY
			  	         	FROM SNMPv2-SMI
			DisplayString 
										FROM SNMPv2-TC        	  	         	
			l2PortManage
										FROM TLSG5412F-L2SWITCH-MIB;

   		l2PortSecurity MODULE-IDENTITY  
	    LAST-UPDATED    "200908270000Z"
	    ORGANIZATION    "TPLINK"
	    CONTACT-INFO		"www.tplink.com.cn"
	    DESCRIPTION			"The config of the port security."
	    REVISION        "200908270000Z"
	    DESCRIPTION			"Initial version of this MIB module."
	    ::= { l2PortManage 3 } 
	    
  		l2PortSecurityTable	OBJECT-TYPE
  			SYNTAX			SEQUENCE OF PortSecurityEntry
  			MAX-ACCESS 	not-accessible
  			STATUS 			current
  			DESCRIPTION 
  			"A table that contains security information about every port.
  			Port Security is to protect the switch from the malicious MAC 
  			address attack by limiting the maximum number of MAC addresses
  			that can be learned on the port. The port with Port Security 
  			feature enabled will learn the MAC address dynamically. When
  			the learned MAC address number reaches the maximum, the port
  			will stop learning. Thereafter, the other devices with the MAC
  			address unlearned can not access to the network via this port."
  			::= {l2PortSecurity 1}
  			
  		l2PortSecurityEntry OBJECT-TYPE
  			SYNTAX			PortSecurityEntry
  			MAX-ACCESS	not-accessible
  			STATUS			current
  			DESCRIPTION	
  			"A list security information for each port of the device."
  			INDEX{l2PortSecurityPortIndex}
  			::= {l2PortSecurityTable 1}
  			
  		PortSecurityEntry	::=
  		SEQUENCE
  		{
  			l2PortSecurityPortIndex
  				INTEGER,
  			l2PortSecurityMaxNum
  				INTEGER,
  			l2PortSecurityLearnNum
  				INTEGER,
  			l2PortSecurityLearnMode
  				INTEGER,
  			l2PortSecurityPortStatus
  				INTEGER
  		}
  		
  		l2PortSecurityPortIndex OBJECT-TYPE
  			SYNTAX			INTEGER
  			MAX-ACCESS	read-only
  			STATUS			current
  			DESCRIPTION	
  			"This object indicates the port number."
  			::= {l2PortSecurityEntry 1}
  			
  		l2PortSecurityMaxNum OBJECT-TYPE
  			SYNTAX			INTEGER(0..64)
  			MAX-ACCESS	read-write
  			STATUS			current
  			DESCRIPTION	
  			"This object indicates the maximum number of MAC addresses that
  			can be learned on the port."
  			::= {l2PortSecurityEntry 2}
  			
  		l2PortSecurityLearnNum OBJECT-TYPE
  			SYNTAX			INTEGER
  			MAX-ACCESS	read-only
  			STATUS			current
  			DESCRIPTION	
  			"This object indicates the number of MAC addresses that have been
  			learned on the port."
  			::= {l2PortSecurityEntry 3}
  		
  		l2PortSecurityLearnMode	OBJECT-TYPE
  			SYNTAX			
  				INTEGER
  				{
  					dynamic(0),
  					static(1),
  					permanent(2)
  				}
  			MAX-ACCESS	read-write
  			STATUS			current
  			DESCRIPTION	
  			"This object indicates the learn mode of the port.
  			
  			dynamic: When dynamic mode is selected, the learned MAC address
  			will be deleted automatically after the aging time.
  			
  			static: When static mode is selected, the learned MAC address will
  			be out of the influence of the aging time and can only be deleted 
  			manually. The learned entries will be cleared after the switch is 
  			rebooted.
  			
  			permanent: When permanent mode is selected, the learned MAC address 
  			will be out of the influence of the aging time and can only be 
  			deleted manually. The learned entries will be saved even the switch
  			is rebooted. "
  			
  			::= {l2PortSecurityEntry 4}
  			
  		l2PortSecurityPortStatus OBJECT-TYPE
  			SYNTAX			
  			INTEGER
  			{
  				disable(0),
  				enable(1)
  			}
  			MAX-ACCESS	read-write
  			STATUS			current
  			DESCRIPTION	
  			"This object indicates the security feature of the port."
  			::= {l2PortSecurityEntry 5}						          	  	          
END
