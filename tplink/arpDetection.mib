TLSG5412F-ARP-DETECTION-MIB DEFINITIONS ::= BEGIN

         IMPORTS
            OBJECT-TYPE
          	  	         	FROM SNMPv2-SMI
            arpDetection	          
          	  	          FROM TLSG5412F-ARP-DEFENSE-MIB; 
          	  	          
			 	arpDetectionConfig  	OBJECT IDENTIFIER ::= {arpDetection 1}
        arpDetectionStat 			OBJECT IDENTIFIER ::= {arpDetection 2}
             
        -- the arp defend cheat config
    		arpDetectionConfigEnable OBJECT-TYPE
	          SYNTAX  INTEGER{
	      		disable(0), 						
	      		enable(1)			
	      		}
	            MAX-ACCESS  read-write
	            STATUS  current
	            DESCRIPTION
	                    "0. disable
	                     1. enable
	                     Enable/Disable the ARP Detect function."
	            ::= { arpDetectionConfig 1 }	
        
         arpDetectionTrustPortTable OBJECT-TYPE
            SYNTAX  SEQUENCE OF ARPDEFENDCHEATCONFIGENTRY
            MAX-ACCESS  not-accessible
            STATUS  current
            DESCRIPTION
                    "A list of trusted port config entries.
                     Here you can configure the Trusted Port."
            ::= { arpDetectionConfig 2 }
         
        arpDetectionTrustPortEntry OBJECT-TYPE
            SYNTAX  ARPDEFENDCHEATCONFIGENTRY
            MAX-ACCESS  not-accessible
            STATUS  current
            DESCRIPTION
                    "An entry contains of the information of arp defend trust port."
            INDEX   { arpDetectionTrustPort }
            ::= { arpDetectionTrustPortTable 1 }
    
        ARPDEFENDCHEATCONFIGENTRY ::=
            SEQUENCE {
								arpDetectionTrustPort
										INTEGER, 
								arpDetectionTrustPortState
										INTEGER,
								arpDetectionTrustPortLag
										OCTET STRING (SIZE (1..255)) 
            }
            
        arpDetectionTrustPort OBJECT-TYPE
            SYNTAX  INTEGER  
            MAX-ACCESS  read-only
            STATUS  current
            DESCRIPTION
                    "The port for which the ARP Detect function is unnecessary as the Trusted Port. 
                     The specific ports, such as up-linked port, routing port and LAG port, 
                     should be set as Trusted Port. To ensure the normal communication of the switch, 
                     please configure the ARP Trusted Port before enabling the ARP Detect function. "
            ::= { arpDetectionTrustPortEntry 1 }
        
        arpDetectionTrustPortState OBJECT-TYPE
            SYNTAX  INTEGER{
	      		trustful(1),
	      		untrusty(0)					
	      		}
            MAX-ACCESS  read-write
            STATUS  current
            DESCRIPTION
                    "0. untrusty port
                     1. trustful port"
            ::= { arpDetectionTrustPortEntry 2 }
        
        arpDetectionTrustPortLag OBJECT-TYPE
            SYNTAX  OCTET STRING (SIZE (1..255))  
            MAX-ACCESS  read-only
            STATUS  current
            DESCRIPTION
                    "the lag the port belong to"
            ::= { arpDetectionTrustPortEntry 3 }
       
       -- the arp defend cheat statics
       arpDetectionStatReset OBJECT-TYPE
	          SYNTAX  INTEGER{
	      		notReset(0), 						
	      		reset(1)			
	      		}
	            MAX-ACCESS  read-write
	            STATUS  current
	            DESCRIPTION
	                    "0. notReset
	                     1. reset
	                     clear the statistics"
	            ::= { arpDetectionStat 1 }
	            
        arpDetectionStatTable OBJECT-TYPE
            SYNTAX  SEQUENCE OF ARPDEFENDCHEATSTATENTRY
            MAX-ACCESS  not-accessible
            STATUS  current
            DESCRIPTION
                    "A list of arp detection Stat entries.
                    Here you can view the statistics of the illegal ARP packets received by each port."
            ::= { arpDetectionStat 2 }
       
       arpDetectionStatEntry OBJECT-TYPE
            SYNTAX  ARPDEFENDCHEATSTATENTRY
            MAX-ACCESS  not-accessible
            STATUS  current
            DESCRIPTION
                    "An entry contains of the information of arp defend nonlegal pkt."
            INDEX   { arpDetectionStatPort }
            ::= { arpDetectionStatTable 1 }
    
        ARPDEFENDCHEATSTATENTRY ::=
            SEQUENCE {
								arpDetectionStatPort
										INTEGER, 
								arpDetectionStatState
										INTEGER,
								arpDetectionStatNonLegalPkt
										Counter32
            }
            
        arpDetectionStatPort OBJECT-TYPE
            SYNTAX  INTEGER  
            MAX-ACCESS  read-only
            STATUS  current
            DESCRIPTION
                    "port number"
            ::= { arpDetectionStatEntry 1 }
        
        arpDetectionStatState OBJECT-TYPE
            SYNTAX  INTEGER{
	      		trustful(1),
	      		untrusty(0)					
	      		}
            MAX-ACCESS  read-only
            STATUS  current
            DESCRIPTION
                    "0. untrusty port
                     1. trustful port"
            ::= { arpDetectionStatEntry 2 }
            
          arpDetectionStatNonLegalPkt OBJECT-TYPE
            SYNTAX  Counter32  
            MAX-ACCESS  read-only
            STATUS  current
            DESCRIPTION
                    "Displays the number of the received illegal ARP packets."
            ::= { arpDetectionStatEntry 3 }
END
