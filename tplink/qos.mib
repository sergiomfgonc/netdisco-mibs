TLSG5412F-QOS-MIB DEFINITIONS ::= BEGIN

       IMPORTS
          OBJECT-TYPE
        	  	         	FROM SNMPv2-SMI
          qos	          
        	  	          FROM  TLSG5412F-SERVICE-QUALITY-MIB; 
          	  	          
			 	qosBasicConfig  	OBJECT IDENTIFIER ::= {qos 1}
        qosScheduler  		OBJECT IDENTIFIER ::= {qos 2}
  			qos8021p					OBJECT IDENTIFIER ::= {qos 3}
  			qosDSCP						OBJECT IDENTIFIER ::= {qos 4}
  			           
        -- the qos basic config
              
         qosBasicConfigTable OBJECT-TYPE
            SYNTAX  SEQUENCE OF QOSBASICCONFIGENTRY
            MAX-ACCESS  not-accessible
            STATUS  current
            DESCRIPTION
                    "A list of qos basic config entries. Here you can configure the port priority."
            ::= { qosBasicConfig 1 }

        qosBasicConfigEntry OBJECT-TYPE
            SYNTAX  QOSBASICCONFIGENTRY
            MAX-ACCESS  not-accessible
            STATUS  current
            DESCRIPTION
                    "An entry contains of the information of qos basic config."
            INDEX   { qosBasicConfigPort }
            ::= { qosBasicConfigTable 1 }
    
        QOSBASICCONFIGENTRY ::=
            SEQUENCE {
								qosBasicConfigPort
										INTEGER, 
								qosBasicConfigPri
										INTEGER,
								qosBasicConfigLag
										OCTET STRING (SIZE (1..255))
										
            }
            
        qosBasicConfigPort OBJECT-TYPE
            SYNTAX  INTEGER  
            MAX-ACCESS  read-only
            STATUS  current
            DESCRIPTION
                    "The physical port number of the switch. "
            ::= { qosBasicConfigEntry 1 }
        
        qosBasicConfigPri OBJECT-TYPE
            SYNTAX  INTEGER{
	      		cos0(0), 						
	      		cos1(1),
	      		cos2(2),
	      		cos3(3),
	      		cos4(4),
	      		cos5(5),
	      		cos6(6),		
	      		cos7(7)					
	      		}
            MAX-ACCESS  read-write
            STATUS  current
            DESCRIPTION
                    "0. Cos0
                     1. Cos1
                     2. Cos2
                     3. Cos3
                     4. Cos4
                     5. Cos5
                     6. Cos6
                     7. Cos7
                     Specify the priority for the port."
            ::= { qosBasicConfigEntry 2 }
       
      qosBasicConfigLag OBJECT-TYPE
            SYNTAX  OCTET STRING (SIZE (1..255))  
            MAX-ACCESS  read-only
            STATUS  current
            DESCRIPTION
                    "The LAG number which the port belongs to. "
            ::= { qosBasicConfigEntry 3 }
         
       qosSchedulerConfig OBJECT-TYPE
	          SYNTAX  INTEGER{
	      		sp-mode(0), 						
	      		wrr-mode(1),
	      		sp-wrr-mode(2),
	      		equ-mode(3)						
	      		}
	            MAX-ACCESS  read-write
	            STATUS  current
	            DESCRIPTION
	                    "Here you can select the schedule mode for the switch.
	                     0. SP-Mode: Strict-Priority Mode. 
	                        In this mode, the queue with higher priority will occupy the whole bandwidth. 
	                        Packets in the queue with lower priority are sent only when the queue with 
	                        higher priority is empty.  
	                     1. WRR-Mode: Weight Round Robin Mode. 
	                        In this mode, packets in all the queues are sent in order based on the weight 
	                        value for each queue. 
	                        The weight value ratio of TC0, TC1, TC2 and TC3 is 1:2:4:8. 
	                     2. SP+WRR-Mode: SP+Strict-Priority + Weight Round Robin Mode. 
	                        In this mode, this switch provides two scheduling groups, SP group and WRR group. 
	                        Queues in SP group and WRR group are scheduled strictly based on strict-priority mode 
	                        while the queues inside WRR group follow the WRR mode. 
	                        In SP+WRR mode, TC3 is in the SP group; TC0, TC1 and TC2 belong to the WRR group and 
	                        the weight value ratio of TC0, TC1 and TC2 is 1:2:4. 
	                        In this way, when scheduling queues, the switch allows TC3 to occupy the whole bandwidth 
	                        following the SP mode and the TC0, TC1 and TC2 in the WRR group will take up the bandwidth
	                        according to their ratio 1:2:4. 
	                     3. Equ-Mode: Equal-Mode. 
	                        In this mode, all the queues occupy the bandwidth equally. 
	                        The weight value ratio of all the queues is 1:1:1:1. "
	            ::= { qosScheduler 1 }
	            
  			-- the qos 8021p config
        
        qos8021pEnable OBJECT-TYPE
	          SYNTAX  INTEGER{
	      		disable(0), 						
	      		enable(1)			
	      		}
	            MAX-ACCESS  read-write
	            STATUS  current
	            DESCRIPTION
	                    "0. disable
	                     1. enable
	                     Here you can enable or disable 802.1P Priority."
	            ::= { qos8021p 1 }	
        
         qos8021pTable OBJECT-TYPE
            SYNTAX  SEQUENCE OF QOS8021PENTRY
            MAX-ACCESS  not-accessible
            STATUS  current
            DESCRIPTION
                    "A list of qos 8021p entries.
                     Here you can configure 802.1P Priority."
            ::= { qos8021p 2 }

        qos8021pEntry OBJECT-TYPE
            SYNTAX  QOS8021PENTRY
            MAX-ACCESS  not-accessible
            STATUS  current
            DESCRIPTION
                    "An entry contains of the information of qos 8021p."
            INDEX   { qos8021pPriTag }
            ::= { qos8021pTable 1 }
    
        QOS8021PENTRY ::=
            SEQUENCE {
                qos8021pPriTag
										INTEGER,
                qos8021pPriLevel
										INTEGER
            }
            
        qos8021pPriTag OBJECT-TYPE
            SYNTAX  INTEGER
            MAX-ACCESS  read-only
            STATUS  current
            DESCRIPTION
                    "Indicates the precedence level defined by IEEE802.1P. "
            ::= { qos8021pEntry 1 }
        
        qos8021pPriLevel OBJECT-TYPE
            SYNTAX  INTEGER{
            			tc0(0),
            			tc1(1),
            			tc2(2),
            			tc3(3)
            }
            MAX-ACCESS  read-write
            STATUS  current
            DESCRIPTION
                    "Indicates the priority level the packets with tag are mapped to. 
                     The priority levels are labeled as TC 0, TC1, TC2 and TC3."
            ::= { qos8021pEntry 2 }
        
       -- the qos dscp config
        
        qosDSCPEnable OBJECT-TYPE
	          SYNTAX  INTEGER{
	      		disable(0), 						
	      		enable(1)		
	      		}
	            MAX-ACCESS  read-write
	            STATUS  current
	            DESCRIPTION
	                    "0. disable
	                     1. enable
	                     Here you can enable or disable DSCP Priority."
	            ::= { qosDSCP 1 }	
        
         qosDSCPTable OBJECT-TYPE
            SYNTAX  SEQUENCE OF QOSDSCPENTRY
            MAX-ACCESS  not-accessible
            STATUS  current
            DESCRIPTION
                    "A list of qos DSCP entries.
                     Here you can configure DSCP Priority."
            ::= { qosDSCP 2 }

        qosDSCPEntry OBJECT-TYPE
            SYNTAX  QOSDSCPENTRY
            MAX-ACCESS  not-accessible
            STATUS  current
            DESCRIPTION
                    "An entry contains of the information of qos DSCP."
            INDEX   { qosDSCPPriTag }
            ::= { qosDSCPTable 1 }
    
        QOSDSCPENTRY ::=
            SEQUENCE {
                qosDSCPPriTag
										INTEGER,
                qosDSCPPriLevel
										INTEGER
            }
            
        qosDSCPPriTag OBJECT-TYPE
            SYNTAX  INTEGER
            MAX-ACCESS  read-only
            STATUS  current
            DESCRIPTION
                    "Indicates the priority determined by the DS region of IP datagram. 
                     It ranges from 0 to 63. "
            ::= { qosDSCPEntry 1 }
        
        qosDSCPPriLevel OBJECT-TYPE
            SYNTAX  INTEGER{
            			tc0(0),
            			tc1(1),
            			tc2(2),
            			tc3(3)
            }
            MAX-ACCESS  read-write
            STATUS  current
            DESCRIPTION
                    "Indicates the priority level the packets with tag are mapped to. 
                     The priority levels are labeled as TC 0, TC1, TC2 and TC3."
            ::= { qosDSCPEntry 2 }
END
