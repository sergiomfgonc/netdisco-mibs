-- Performance multicast group show
-- modify history: not change
--    

TLSG5412F-IGMP-MULTICASTGROUP-MIB DEFINITIONS ::= BEGIN

          IMPORTS
		IpAddress
                      FROM RFC1155-SMI
              OBJECT-TYPE,MODULE-IDENTITY
          	  	         	FROM SNMPv2-SMI
              	igmpMultigroup	          
          	  	          	FROM  TLSG5412F-IGMP-MANAGE-MIB;
          	  	          	
          	  	          	        	
       		
       	igmpMulticastGroups MODULE-IDENTITY  
			    LAST-UPDATED    "200812160000Z"
			    ORGANIZATION    "TPLINK"
			    CONTACT-INFO		"www.tplink.com.cn"
			    DESCRIPTION
			             "Here you can view the information of the multicast 
			              groups already on the switch."
			    REVISION        "201207120000Z"
			    DESCRIPTION
					"Initial version of this MIB module."
			    ::= { igmpMultigroup 1 }      	      
      	   

          
          
          igmpMulticastGroupTable OBJECT-TYPE
              SYNTAX  SEQUENCE OF MULTIGROUPENTRY
              MAX-ACCESS  not-accessible
              STATUS  current
              DESCRIPTION
                      "A list of  multicast groups Table."
              ::= { igmpMulticastGroups 1 }

          igmpMulticastGroupEntry OBJECT-TYPE
              SYNTAX  MULTIGROUPENTRY
              MAX-ACCESS  not-accessible
              STATUS  current
              DESCRIPTION
                      "An entry contains of multicast packet statistics over each port."
              INDEX   { igmpMulticastIP ,  igmpVlanID}
              ::= { igmpMulticastGroupTable 1 }
      
          MULTIGROUPENTRY ::=
              SEQUENCE {
                  igmpMulticastIP
                      IpAddress,
                 igmpVlanID
              				INTEGER,
                  igmpForwardPorts
                      OCTET STRING(SIZE (0..50)),
                  igmpGrouptype
                      INTEGER
              }
                 
            igmpMulticastIP OBJECT-TYPE
            	 SYNTAX  IpAddress
              MAX-ACCESS  read-only
              STATUS  current
              DESCRIPTION
                      "Displays the multicast IP address."
              ::= { igmpMulticastGroupEntry 1 }
              
            igmpVlanID OBJECT-TYPE
            	 SYNTAX  INTEGER
              MAX-ACCESS  read-only
              STATUS  current
              DESCRIPTION
                      "Displays the VLAN ID."
              ::= { igmpMulticastGroupEntry 2 }
           
            igmpForwardPorts OBJECT-TYPE
            	 SYNTAX  OCTET STRING(SIZE (0..50))
              MAX-ACCESS  read-only
              STATUS  current
              DESCRIPTION
                      "Displays the forward ports of multicast group."
              ::= { igmpMulticastGroupEntry 3 }
                 
          igmpGrouptype OBJECT-TYPE
            	 SYNTAX  INTEGER{
	      		static(0), 						
	      		dynamic(1)						
	      		}
              MAX-ACCESS  read-only
              STATUS  current
              DESCRIPTION
                      "Displays the type of multicast group."
              ::= { igmpMulticastGroupEntry 4 }
              
       
          END
