TLSG5412F-CLUSTER-MIB DEFINITIONS ::= BEGIN

         IMPORTS
            MODULE-IDENTITY
          	  	         	FROM SNMPv2-SMI    	  	         	
            tlsg5412f	          
          	  	          FROM TPLINK; 

	    clusterMIB MODULE-IDENTITY
		    LAST-UPDATED    "200908270000Z"
		    ORGANIZATION    "TPLINK"
		    CONTACT-INFO		"www.tplink.com.cn"
	   	 	DESCRIPTION			"Cluster Management function enables a network administer to 
									   	 	manage the scattered devices in the network via a management
									   	 	device. After a commander switch is configured, management 
									   	 	and maintenance operations intended for the member devices 
									   	 	in a cluster is implemented by the commander device. "
		    REVISION        "200908270000Z"
		    DESCRIPTION			"Initial version of this MIB module."	   	    
	    	::= { tlsg5412f 10 }
	    	
	    ndpManage		OBJECT IDENTIFIER 	::= {clusterMIB 1}
	    ntdpManage 	OBJECT IDENTIFIER 	::= {clusterMIB 2}
	    clusterManage	OBJECT IDENTIFIER	::= {clusterMIB 3}
END
