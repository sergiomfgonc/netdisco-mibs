TLSG5412F-ARP-DEFEND-MIB DEFINITIONS ::= BEGIN

         IMPORTS
            OBJECT-TYPE
          	  	         	FROM SNMPv2-SMI
            arpDefend	          
          	  	          FROM TLSG5412F-ARP-DEFENSE-MIB; 
          	  	          
			 	arpDefendConfig  	OBJECT IDENTIFIER ::= {arpDefend 1}
             
        -- the arp defend  config
         arpDefendConfigTable OBJECT-TYPE
            SYNTAX  SEQUENCE OF ARPDEFENDATTACKCONFIGENTRY
            MAX-ACCESS  not-accessible
            STATUS  current
            DESCRIPTION
                    "A list of arp defend config entries.
                     Here you can configure the ARP Defend feature."
            ::= { arpDefendConfig 1 }
         
        arpDefendConfigEntry OBJECT-TYPE
            SYNTAX  ARPDEFENDATTACKCONFIGENTRY
            MAX-ACCESS  not-accessible
            STATUS  current
            DESCRIPTION
                    "An entry contains of the information of arp defend attack config."
            INDEX   { arpDefendConfigPort }
            ::= { arpDefendConfigTable 1 }
    
        ARPDEFENDATTACKCONFIGENTRY ::=
            SEQUENCE {
								arpDefendConfigPort
										INTEGER, 
								arpDefendConfigEnable
										INTEGER,
								arpDefendConfigRate
										INTEGER,
								arpDefendConfigState
										OCTET STRING (SIZE (1..255)),
								arpDefendConfigPortLag
										OCTET STRING (SIZE (1..255))
            }
            
        arpDefendConfigPort OBJECT-TYPE
            SYNTAX  INTEGER  
            MAX-ACCESS  read-only
            STATUS  current
            DESCRIPTION
                    "port number"
            ::= { arpDefendConfigEntry 1 }
        
        arpDefendConfigEnable OBJECT-TYPE
            SYNTAX  INTEGER{
	      		enable(1),
	      		disable(0)					
	      		}
            MAX-ACCESS  read-write
            STATUS  current
            DESCRIPTION
                    "0. disable
                     1. enable
                     Select Enable/Disable the ARP Defend feature for the port. "
            ::= { arpDefendConfigEntry 2 }
       
       arpDefendConfigRate OBJECT-TYPE
            SYNTAX  INTEGER  
            MAX-ACCESS  read-write
            STATUS  current
            DESCRIPTION
                    "specify the maximum amount of the received ARP packets per second.(10-100pps)"
            ::= { arpDefendConfigEntry 3 }
            
       arpDefendConfigState OBJECT-TYPE
           	SYNTAX  OCTET STRING (SIZE (1..255))
            MAX-ACCESS  read-only
            STATUS  current
            DESCRIPTION
                    "the state of port, when the rate exceed, the port will discard the arp pkt."
            ::= { arpDefendConfigEntry 4 }
            
      arpDefendConfigPortLag OBJECT-TYPE
            SYNTAX  OCTET STRING (SIZE (1..255))  
            MAX-ACCESS  read-only
            STATUS  current
            DESCRIPTION
                    "the lag the port belong to"
            ::= { arpDefendConfigEntry 5 }
END
