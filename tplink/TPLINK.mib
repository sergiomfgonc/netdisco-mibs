-- file: TPLINK.my
-- Changes:
--      Converted to SMIC format.


TPLINK DEFINITIONS ::= BEGIN

--iso             OBJECT IDENTIFIER ::= { 1 }
--org             OBJECT IDENTIFIER ::= { iso 3 }
--dod             OBJECT IDENTIFIER ::= { org 6 }
--internet        OBJECT IDENTIFIER ::= { dod 1 }
--private         OBJECT IDENTIFIER ::= { internet 4 }
--enterprises     OBJECT IDENTIFIER ::= { private 1 }

    IMPORTS
        enterprises FROM RFC1155-SMI;

tplink 		OBJECT IDENTIFIER ::= { enterprises 11863 }
switch		OBJECT IDENTIFIER ::= { tplink 1 }
router		OBJECT IDENTIFIER ::= { tplink 2 }
wireless	OBJECT IDENTIFIER ::= { tplink 3 }
adsl		OBJECT IDENTIFIER ::= { tplink 4 }

l2manageswitch	OBJECT IDENTIFIER ::= { switch 1 }
l3manageswitch	OBJECT IDENTIFIER ::= { switch 2 }

tlsl5428	OBJECT IDENTIFIER ::= { l2manageswitch 1 }
tlsl3428	OBJECT IDENTIFIER ::= { l2manageswitch 2 }
tlsg3424	OBJECT IDENTIFIER ::= { l2manageswitch 3 }
tlsg3216	OBJECT IDENTIFIER ::= { l2manageswitch 4 }
tlsg3210	OBJECT IDENTIFIER ::= { l2manageswitch 5 }
tlsl3428un	OBJECT IDENTIFIER ::= { l2manageswitch 6 }
tlsg5428  	OBJECT IDENTIFIER ::= { l2manageswitch 7 }
tlsg5412f 	OBJECT IDENTIFIER ::= { l2manageswitch 9 }    

END
