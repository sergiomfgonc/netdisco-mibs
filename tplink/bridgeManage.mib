TLSG5412F-BRIDGEMANAGE-MIB DEFINITIONS ::= BEGIN
       
       IMPORTS
	    RowStatus       	 
  					FROM SNMPv2-TC
            OBJECT-TYPE
          	  	         	FROM SNMPv2-SMI
            l2BridgeManage
					FROM TLSG5412F-L2SWITCH-MIB;
          	  	          
       MacAddress ::= OCTET STRING (SIZE (6))
	    
	l2BridgeManageStaticAddrCtrl	  	OBJECT IDENTIFIER ::= {l2BridgeManage 1}
        l2BridgeManageDynAddrCtrl 		OBJECT IDENTIFIER ::= {l2BridgeManage 2}
        l2BridgeManageFilterAddrCtrl 		OBJECT IDENTIFIER ::= {l2BridgeManage 3}
        l2BridgeManageNotifications  		OBJECT IDENTIFIER ::= {l2BridgeManage 4} 
        
        fdbDynMacNew NOTIFICATION-TYPE
        	OBJECTS
        	{   
        		l2BridgeManageDynPort	
        	}
        	STATUS current
        	DESCRIPTION 
        		"The switch has learned a new dynamic address."         	 
            ::= { l2BridgeManageNotifications 1 }        
            
        fdbStaticMacNew NOTIFICATION-TYPE
        	OBJECTS
        	{   
        		l2BridgeManageStaticPort
           	}
        	STATUS current
        	DESCRIPTION 
        		"The switch has learned a new static address."         	 
            ::= { l2BridgeManageNotifications 2 } 
            
        fdbFilterMacNew NOTIFICATION-TYPE
        	OBJECTS
        	{   
        		l2BridgeManageFilterVlanId
           	}
        	STATUS current
        	DESCRIPTION 
        		"The switch has learned a new filter address."         	 
            ::= { l2BridgeManageNotifications 3 }     
    

            
        fdbMacTableFull NOTIFICATION-TYPE
        	OBJECTS
        	{
        		l2BridgeManageStaticPort			
        	}
        	STATUS current
        	DESCRIPTION 
        		"The switch's Address Table is full!"         	 
            ::= { l2BridgeManageNotifications 4 }  
            
        fdbMacMaxLearnedNumExceed NOTIFICATION-TYPE
        	OBJECTS
        	{
        		l2BridgeManageStaticPort		
        	}
        	STATUS current
        	DESCRIPTION 
        		"The l2BridgeManageStaticPort has learned the maximum number of address that it can learn."         	 
            ::= { l2BridgeManageNotifications 5 }      
            
        fdbMacLearnModeChange NOTIFICATION-TYPE
        	OBJECTS
        	{
      			l2BridgeManageStaticPort		
        	}
        	STATUS current
        	DESCRIPTION 
        		"The l2BridgeManageDynPort has opened its portSecurity, and changes its learning mode."         	 
            ::= { l2BridgeManageNotifications 6 }  

        
        l2BridgeManageStaticAddrCtrlTable OBJECT-TYPE
              SYNTAX  SEQUENCE OF STATICADDRCTRLENTRY
              MAX-ACCESS  not-accessible
              STATUS  current
              DESCRIPTION
                      "A list of static mac address entries."
              ::= { l2BridgeManageStaticAddrCtrl 1 }
        
        l2BridgeManageStaticAddrCtrlEntry OBJECT-TYPE
              SYNTAX  STATICADDRCTRLENTRY
              MAX-ACCESS  not-accessible
              STATUS  current
              DESCRIPTION
                      "   The static address can be added or removed manually, independent of the aging time.
                       In the stable networks, the static MAC address entries can facilitate the switch to 
                       reduce broadcast packets and enhance the efficiency of packets forwarding remarkably."
              INDEX   { l2BridgeManageStaticMac,l2BridgeManageStaticVlanId }
              ::= { l2BridgeManageStaticAddrCtrlTable 1 }
              
              
        STATICADDRCTRLENTRY ::=
              SEQUENCE {
                  l2BridgeManageStaticMac
                      MacAddress, 
                  l2BridgeManageStaticVlanId
                  	INTEGER,
                  l2BridgeManageStaticPort
                      INTEGER,
                  l2BridgeManageStaticStatus
                  	RowStatus
              }
              
         l2BridgeManageStaticMac OBJECT-TYPE
              SYNTAX  MacAddress  
              MAX-ACCESS  read-only
              STATUS  current
              DESCRIPTION
                      "The static MAC Address"
              ::= { l2BridgeManageStaticAddrCtrlEntry 1 }
            
         l2BridgeManageStaticVlanId  OBJECT-TYPE
             SYNTAX  INTEGER  
              MAX-ACCESS  read-only
              STATUS  current
              DESCRIPTION
                      "The corresponding VLAN ID of the MAC address."
              ::= { l2BridgeManageStaticAddrCtrlEntry 2 }
           
	   l2BridgeManageStaticPort  OBJECT-TYPE
	     SYNTAX  INTEGER  
	      MAX-ACCESS  read-create
	      STATUS  current
	      DESCRIPTION
	              "The corresponding Port number of the MAC address."
	      ::= { l2BridgeManageStaticAddrCtrlEntry 3 }

	      
	  l2BridgeManageStaticStatus  OBJECT-TYPE
	     SYNTAX  RowStatus  
	      MAX-ACCESS  read-create
	      STATUS  current
	      DESCRIPTION
	             "  The following values are states:
                     these values may be used as follow:
                     
                     active(1),if the entry is being used.
                     notInService(2),destroy the entry.
                     notReady(3),destroy the entry.
                     createAndGo(4),not being used.
                     createAndWait(5),create a new entry.
                     destroy(6),destroy the entry."
	      ::= { l2BridgeManageStaticAddrCtrlEntry 4 }
	      
	    
        
       l2BridgeManageDynAddrCtrlAgingTime OBJECT-TYPE
	       SYNTAX   INTEGER
	       MAX-ACCESS   read-write
	       STATUS   current
	       DESCRIPTION
               "Configure aging time for the dynamic address.Set 0 to disable auto aging."
		::= { l2BridgeManageDynAddrCtrl 1}
       
       l2BridgeManageDynAddrCtrlTable OBJECT-TYPE
              SYNTAX  SEQUENCE OF DYNADDRCTRLENTRY
              MAX-ACCESS  not-accessible
              STATUS  current
              DESCRIPTION
                      "A list of dynamic MAC address entries."
              ::= { l2BridgeManageDynAddrCtrl 2 }
             
        l2BridgeManageDynAddrCtrlEntry OBJECT-TYPE
              SYNTAX  DYNADDRCTRLENTRY
              MAX-ACCESS  not-accessible
              STATUS  current
              DESCRIPTION
                      "  The dynamic address can be generated by the auto-learning mechanism of the switch. 
                      The Dynamic Address Table can update automatically by auto-learning or aging out the 
                      MAC address."
              INDEX   {l2BridgeManageDynMac,l2BridgeManageDynVlanId }
              ::= { l2BridgeManageDynAddrCtrlTable 1 }
              
               
        DYNADDRCTRLENTRY ::=
              SEQUENCE {
                  l2BridgeManageDynMac
                      MacAddress, 
                  l2BridgeManageDynVlanId
                  	INTEGER,
                  l2BridgeManageDynPort
                      OCTET STRING (SIZE (1..6)),
                  l2BridgeManageDynAgeStatus
                      	INTEGER,
                  l2BridgeManageDynStatus
                  	INTEGER
              }
              
         l2BridgeManageDynMac OBJECT-TYPE
              SYNTAX  MacAddress  
              MAX-ACCESS  read-only
              STATUS  current
              DESCRIPTION
                      "The dynamic MAC Address."
              ::= { l2BridgeManageDynAddrCtrlEntry 1 }
            
         l2BridgeManageDynVlanId  OBJECT-TYPE
             SYNTAX  INTEGER  
              MAX-ACCESS  read-only
              STATUS  current
              DESCRIPTION
                      "Displays the corresponding VLAN ID of the MAC address."
              ::= { l2BridgeManageDynAddrCtrlEntry 2 }
           
	  l2BridgeManageDynPort  OBJECT-TYPE
	     SYNTAX  OCTET STRING (SIZE (1..6))  
	      MAX-ACCESS  read-write
	      STATUS  current
	      DESCRIPTION
	              "The corresponding port number of the MAC address."
	      ::= { l2BridgeManageDynAddrCtrlEntry 3 }
	      
	  l2BridgeManageDynAgeStatus  OBJECT-TYPE
	     SYNTAX  INTEGER {
	      		noAging(0), 			
	      		aging(1)					
	      		} 
	      MAX-ACCESS  read-only
	      STATUS  current
	      DESCRIPTION
	              "The Aging Status of the MAC address."
	      ::= { l2BridgeManageDynAddrCtrlEntry 4 }
	      
	  l2BridgeManageDynStatus  OBJECT-TYPE
	      SYNTAX    INTEGER {
	      		disable(0), 			
	      		enable(1)					
	      		} 
	      MAX-ACCESS  read-write
	      STATUS  current
	      DESCRIPTION
	              "disable(0).....Delete the dynamic MAC entry.
	               enable(1)......It's should be enable when the MAC address is exist."
	      ::= { l2BridgeManageDynAddrCtrlEntry 5 }
	 
	 
	 l2BridgeManageFilterCtrlTable OBJECT-TYPE
              SYNTAX  SEQUENCE OF FILTERADDRCTRLENTRY
              MAX-ACCESS  not-accessible
              STATUS  current
              DESCRIPTION
                      "A list of filter MAC address entries."
              ::= { l2BridgeManageFilterAddrCtrl 1 }
       
        l2BridgeManageFilterCtrlEntry OBJECT-TYPE
              SYNTAX  FILTERADDRCTRLENTRY
              MAX-ACCESS  not-accessible
              STATUS  current
              DESCRIPTION
                      "  The filtering address is to forbid the undesired package to be forwarded. 
                      The filtering address can be added or removed manually, independent of the 
                      aging time."
              INDEX   { l2BridgeManageFilterMac,l2BridgeManageFilterVlanId }
              ::= { l2BridgeManageFilterCtrlTable 1 }
                    
        FILTERADDRCTRLENTRY ::=
              SEQUENCE {
                  l2BridgeManageFilterMac
                      MacAddress, 
                  l2BridgeManageFilterVlanId
                  	INTEGER,
                  l2BridgeManageFilterStatus
                  	RowStatus
              }
              
        l2BridgeManageFilterMac OBJECT-TYPE
              SYNTAX  MacAddress  
              MAX-ACCESS  read-only
              STATUS  current
              DESCRIPTION
                      "The filtering MAC Address."
              ::= { l2BridgeManageFilterCtrlEntry 1 }
            
         l2BridgeManageFilterVlanId  OBJECT-TYPE
             SYNTAX  INTEGER  
              MAX-ACCESS  read-only
              STATUS  current
              DESCRIPTION
                      "The corresponding VLAN ID."
              ::= { l2BridgeManageFilterCtrlEntry 2 }

	      
	 l2BridgeManageFilterStatus  OBJECT-TYPE
	     SYNTAX  RowStatus  
	      MAX-ACCESS  read-create
	      STATUS  current
	      DESCRIPTION
	             " The following values are states:
                     these values may be used as follow:
                     
                     active(1),if the entry is being used.
                     notInService(2),destroy the entry.
                     notReady(3),destroy the entry.
                     createAndGo(4),not being used.
                     createAndWait(5),create a new entry.
                     destroy(6),destroy the entry."
	      ::= { l2BridgeManageFilterCtrlEntry 3 }
	 END
