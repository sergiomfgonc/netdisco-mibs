TLSG5412F-IPPARA-MIB DEFINITIONS ::= BEGIN

          IMPORTS
  
              OBJECT-TYPE,IpAddress
          	  	         	FROM SNMPv2-SMI

              sysConfig	          
          	  	          	FROM TLSG5412F-SYSTEM-MIB;
      	
      	      ipParameter		OBJECT IDENTIFIER ::= {sysConfig 2}
      	      
      
	   ipParaIpMode OBJECT-TYPE
	       SYNTAX  INTEGER{
	      		static(0), 						
	      		dhcp(1),						
	      		bootp(2)						
	      		}
	      MAX-ACCESS  read-only
	      STATUS  current
	      DESCRIPTION
	              "
	              static,set the IPAddress of switch manually.
	              dhcp,if the dhcp host is unclosed, the switch can get its IPAddress through the dhcp client.
	              bootp,if the bootp host is unclosed, the switch can get its IPAddress through the dhcp client.
	              "
	      ::= { ipParameter 1 }
	      
	  ipParaIpAddress OBJECT-TYPE
              SYNTAX  IpAddress
              MAX-ACCESS  read-only
              STATUS  current
              DESCRIPTION
                      "the IPAddress of the switch ,you can set or get its IPAddress via the interface.for example: 192.168.0.1"
              ::= { ipParameter 2 }
              
          ipParaIpMask OBJECT-TYPE
              SYNTAX  IpAddress
              MAX-ACCESS  read-only
              STATUS  current
              DESCRIPTION
                      "the ipMask of the switch.for example: 255.255.255.0"
              ::= { ipParameter 3 }   
          
	  ipParaGateway OBJECT-TYPE
              SYNTAX  IpAddress
              MAX-ACCESS  read-only
              STATUS  current
              DESCRIPTION
                      "the gateway of the switch.for example: 192.168.0.1"
              ::= { ipParameter 4 }
              
          ipParaConfig  OBJECT IDENTIFIER ::= { ipParameter 5 }	
	  ipNotification OBJECT IDENTIFIER ::= { ipParameter 6 }
	  ipAddressChange NOTIFICATION-TYPE
	      OBJECTS{
	              ipMode,
	              ipAddress,
	              ipMask,
	              ipGateway
	              }
	      STATUS current
	      DESCRIPTION
	          "A ipAddressChange notification is sent when one of the parameter of
	           ip address configuration changed"
	      ::={ ipNotification 1 }
          
          ipParaConfigStatic  OBJECT IDENTIFIER ::= { ipParaConfig 1 }
          
          ipParaConfigStaticEnable OBJECT-TYPE
	       SYNTAX  INTEGER{
	      		disable(0), 					
	      		enable(1)					
	      		}
	      MAX-ACCESS  read-write
	      STATUS  current
	      DESCRIPTION
	               "0. disable
                      1.enable"
	      ::= { ipParaConfigStatic 1 }
	      
	  ipParaConfigStaticIpAddress OBJECT-TYPE
              SYNTAX  IpAddress
              MAX-ACCESS  read-write
              STATUS  current
              DESCRIPTION
                      "the IPAddress of the switch ,you can set or get its IPAddress via the interface.for example: 192.168.0.1"
              ::= { ipParaConfigStatic 2 }
              
          ipParaConfigStaticIpMask OBJECT-TYPE
              SYNTAX  IpAddress
              MAX-ACCESS  read-write
              STATUS  current
              DESCRIPTION
                      "the ipMask of the switch.for example: 255.255.255.0"
              ::= { ipParaConfigStatic 3 }   
          
	  ipParaConfigStaticGateway OBJECT-TYPE
              SYNTAX  IpAddress
              MAX-ACCESS  read-write
              STATUS  current
              DESCRIPTION
                      "the gateway of the switch.for example: 192.168.0.1"
              ::= { ipParaConfigStatic 4 }
          
          ipParaConfigDhcpEnable OBJECT-TYPE
	       SYNTAX  INTEGER{
	      		disable(0), 					
	      		enable(1)					
	      		}
	      MAX-ACCESS  read-write
	      STATUS  current
	      DESCRIPTION
	               "0. disable
                       1.enable"
	      ::= { ipParaConfig 2 }
	      
	  ipParaConfigBootpEnable OBJECT-TYPE
	       SYNTAX  INTEGER{
	      		disable(0), 					
	      		enable(1)					
	      		}
	      MAX-ACCESS  read-write
	      STATUS  current
	      DESCRIPTION
	               "0. disable
                        1.enable"
	      ::= { ipParaConfig 3 }
       
       
     	ipParaConfigManageVlan OBJECT-TYPE
	      SYNTAX  INTEGER
	      MAX-ACCESS  read-write
	      STATUS  current
	      DESCRIPTION
	               "This is the only VLAN through which you can get 
	               access to the switch. By default,  VLAN 1 is the 
	               Management VLAN ,you can connect to the switch through 
	               VLAN 1 . However, if other VLAN is set to be the 
	               Management VLAN, you may have to reconnect the 
	               management station to a port that is a member of 
	               the Management VLAN."
	      ::= { ipParaConfig 4 }            
              
      	END
