TLSG5412F-NTDP-MIB DEFINITIONS ::= BEGIN
		IMPORTS
		  OBJECT-TYPE
			  	         	FROM SNMPv2-SMI        	
			ntdpManage
										FROM TLSG5412F-CLUSTER-MIB;
										
		  ntdpGlobalConfig OBJECT IDENTIFIER ::= {ntdpManage 1}
													
	   	ntdpStatus	OBJECT-TYPE
	   		SYNTAX			
	   			INTEGER
	   			{
	   				disable(0),
	   				enable(1)
	   			}
	   		MAX-ACCESS	read-write
	   		STATUS			current
	   		DESCRIPTION	
	   		"This object indicates the ntdp status of the port."
	   		::=	{ntdpGlobalConfig 1}
	   	
	   	ntdpIntervalTime	OBJECT-TYPE
	   		SYNTAX
	   			INTEGER(1..60)
	   		MAX-ACCESS			read-write
	   		STATUS					current
	   		DESCRIPTION			
	   		"This object indicates the interval time of the switch in minute to
	   		periodical send out ntdp packet. The minimum value is 1, maximum value
	   		is 60. "
	   		::=	{ntdpGlobalConfig 2}
	   		
	   	ntdpHop	OBJECT-TYPE
	   		SYNTAX				INTEGER(1..16)
	   		MAX-ACCESS		read-write
	   		STATUS				current
	   		DESCRIPTION	
	   		"This object indicates the hop count the switch topology collects."	   		
	   		::=	{ntdpGlobalConfig 3}
	   		
	   	ntdpHopDelay	OBJECT-TYPE
	   		SYNTAX				INTEGER(1..1000)
	   		MAX-ACCESS		read-write
	   		STATUS				current
	   		DESCRIPTION		
	   		"This object indicates the time between the switch receiving NTDP 
	   		request packets and the switch forwarding NTDP request packets for 
	   		the first time."	   		
	   		::=	{ntdpGlobalConfig 4}
	   		
	   	ntpdPortDelay	OBJECT-TYPE
	   		SYNTAX				INTEGER(1..100)
	   		MAX-ACCESS		read-write
	   		STATUS				current
	   		DESCRIPTION	
	   		"This object indicates the time between the port forwarding NTDP request
	   		packets and its adjacent port forwarding NTDP request packets over."	   		
	   		::=	{ntdpGlobalConfig 5}
	   		
	   	ntdpPortTable	OBJECT-TYPE
	   		SYNTAX 				SEQUENCE OF NtdpPortEntry
	   		MAX-ACCESS		not-accessible
	   		STATUS				current
	   		DESCRIPTION	
	   		"A table that contains ntdp information of every port."	   		
	   		::= {ntdpManage 2}
	   		
	   	ntdpPortEntry OBJECT-TYPE
	   		SYNTAX				NtdpPortEntry
	   		MAX-ACCESS		not-accessible
	   		STATUS				current
	   		DESCRIPTION	
	   		"A list of ntdp information for every port of the device."	   		
	   		INDEX{ntdpPortIndex}
	   		::=	{ntdpPortTable 1}
	   	
	   	NtdpPortEntry ::=
	   	SEQUENCE
	   	{
	   		ntdpPortIndex
	   			INTEGER,
	   		ntdpPortStatus
	   			INTEGER
	   	}
	   	
	   	ntdpPortIndex	OBJECT-TYPE
	   		SYNTAX			INTEGER
	   		MAX-ACCESS	read-only
	   		STATUS			current
	   		DESCRIPTION	
	   		"This object indicates the port number."
	   		::=	{ntdpPortEntry 1}
	   		
	   	ntdpPortStatus	OBJECT-TYPE
	   		SYNTAX
	   			INTEGER
	   			{
	   				disable(0),
	   				enable(1)
	   			}
	   		MAX-ACCESS	read-write
	   		STATUS			current
	   		DESCRIPTION	
	   		"This object indicates the ntdp status of the port."
	   		::=	{ntdpPortEntry 2}
	   		
	   	ntdpCollectTopo	OBJECT-TYPE
	   		SYNTAX			
	   			INTEGER
	   			{
	   				commit(1)
	   			}
	   		MAX-ACCESS	read-write
	   		STATUS			current
	   		DESCRIPTION	
	   		"This object use to collect the topology."
	   		::=	{ntdpManage 4}     
END
