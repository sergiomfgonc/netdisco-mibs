-- Performance Systems config
-- modify history: not change
--    

TLSG5412F-VLAN-GVRP-MIB DEFINITIONS ::= BEGIN

           	 
  					IMPORTS
              OBJECT-TYPE,MODULE-IDENTITY
          	  	         	FROM SNMPv2-SMI
              gvrp          
          	  	          	FROM  TLSG5412F-VLAN-MIB;
          	  	          	
       			gvrpGlobalConfig MODULE-IDENTITY  
			    LAST-UPDATED    "200812160000Z"
			    ORGANIZATION    "TPLINK"
			    CONTACT-INFO		"www.tplink.com.cn"
			    DESCRIPTION
			             "GVRP (GARP VLAN registration protocol) is an implementation of GARP 
			             (generic attribute registration protocol). GVRP allows the switch to 
			             automatically add or remove the VLANs via the dynamic VLAN registration 
			             information and propagate the local VLAN registration information to 
			             other switches, without having to individually configure each VLAN."
			    REVISION        "200812160000Z"
			    DESCRIPTION
					"Initial version of this MIB module."
			    ::= { gvrp 1 }      	      
      	   
            gvrpGlobalEnable OBJECT-TYPE
            SYNTAX  INTEGER{
	      		disable(0), 						--disable
	      		enable(1)						--enable
	      		}
              MAX-ACCESS  read-create
              STATUS  current
              DESCRIPTION
                      "Allows you to Enable/Disable the GVRP function. 
                      0. disable 
                      1. enable"
              ::= { gvrpGlobalConfig 1 }

          
           gvrpPortConfig   	OBJECT IDENTIFIER ::= {gvrp 2}
           gvrpPortTable OBJECT-TYPE
              SYNTAX  SEQUENCE OF PORTENTRY
              MAX-ACCESS  not-accessible
              STATUS  current
              DESCRIPTION
                      "Here you can set the GVRP parameters for each port."
              ::= { gvrpPortConfig 1 }

          gvrpPortEntry OBJECT-TYPE
              SYNTAX  PORTENTRY
              MAX-ACCESS  not-accessible
              STATUS  current
              DESCRIPTION
                      "An entry contains of the information of a port."
              INDEX   { gvrpPortNumber }
              ::= { gvrpPortTable 1 }
      
          PORTENTRY ::=
              SEQUENCE {
              		gvrpPortNumber
              				INTEGER,
                  gvrpPortEnable
                      INTEGER,
                  gvrpPortRegistration
                      INTEGER,
                  gvrpLeaveAllTimer
                  		INTEGER,
                  gvrpJoinTimer
                  		INTEGER,
                  gvrpLeaveTimer
                  		INTEGER,
                  gvrpPortLag
                  		OCTET STRING (SIZE (0..255))
                  	
              }
          gvrpPortNumber OBJECT-TYPE
            	 SYNTAX  INTEGER  
              MAX-ACCESS  read-only
              STATUS  current
              DESCRIPTION
                      "Displays the port number."
              ::= { gvrpPortEntry 1 }
                     
          gvrpPortEnable OBJECT-TYPE
              SYNTAX  INTEGER{
	      		disable(0), 						--Disable
	      		enable(1)						--Enable
	      		}
              MAX-ACCESS  read-write
              STATUS  current
              DESCRIPTION
                      "Enable/Disable the GVRP feature for the port. The port type 
                      should be set to TRUNK before enabling the GVRP feature.
                      0. Disable
                      1. Enable"
              ::= { gvrpPortEntry 2 }
              
          gvrpPortRegistration OBJECT-TYPE
                SYNTAX  INTEGER{
	      				normal(0), 					--NORMAL
	      				fixed(1),						--FIXED
	      				forbidden(2)				--FORBIDDEN
	      				}
              MAX-ACCESS  read-write
              STATUS  current
              DESCRIPTION
                      "Select the Registration Mode for the port.
                      0. NORMAL:In this mode, a port can dynamically register/deregister
                      a VLAN and propagate the dynamic/static VLAN information.
                      1. FIXED:In this mode, a port cannot register/deregister a VLAN
                      dynamically. It only propagates static VLAN information.
                      2. FORBIDDEN:In this mode, a port cannot register/deregister VLANs. 
             					It only propagates VLAN 1 information."
              ::= { gvrpPortEntry 3 }
             
          gvrpLeaveAllTimer OBJECT-TYPE
              SYNTAX  INTEGER (1000..30000)
              MAX-ACCESS  read-write
              STATUS  current
              DESCRIPTION
                      "Once the LeaveAll Timer is set, the port with GVRP enabled 
                      can send a LeaveAll message after the timer times out, so 
                      that other GARP ports can re-register all the attribute information. 
                      After that, the LeaveAll timer will start to begin a new cycle. 
                      The LeaveAll Timer ranges from 1000 to 30000 centiseconds and could 
                      be divided exactly by 5."
              ::= { gvrpPortEntry 4 }
              
     		 gvrpJoinTimer OBJECT-TYPE
              SYNTAX  INTEGER (20..1000)
              MAX-ACCESS  read-write
              STATUS  current
              DESCRIPTION
                      "To guarantee the transmission of the Join messages, a GARP 
                      port sends each Join message two times. The Join Timer is 
                      used to define the interval between the two sending operations 
                      of each Join message. The Join Timer ranges from 20 to 1000 
                      centiseconds and could be divided exactly by 5."
              ::= { gvrpPortEntry 5 }
              
         gvrpLeaveTimer OBJECT-TYPE
              SYNTAX  INTEGER (60..3000)
              MAX-ACCESS  read-write
              STATUS  current
              DESCRIPTION
                      "Once the Leave Timer is set, the GARP port receiving a 
                      Leave message will start its Leave timer, and unregister 
                      the attribute information if it does not receive a Join 
                      message again before the timer times out. The Leave Timer 
                      ranges from 60 to 3000 centiseconds and could be divided 
                      exactly by 5.
                      (leave timer)*10 <= leaveAll timer,
                      (join timer)*2 <= leave timer."
              ::= { gvrpPortEntry 6 }
              
          gvrpPortLag OBJECT-TYPE
          		SYNTAX  OCTET STRING (SIZE (0..255))
              MAX-ACCESS  read-only
              STATUS  current
              DESCRIPTION
                      "Displays the LAG to which the port belongs."
              ::= { gvrpPortEntry 7 }
      	
          END
