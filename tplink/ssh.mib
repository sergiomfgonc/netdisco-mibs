TLSG5412F-SSH-MIB DEFINITIONS ::= BEGIN

          IMPORTS
              OBJECT-TYPE
          	  	         	FROM SNMPv2-SMI
              accessSecurity	          
          	  	          	FROM TLSG5412F-SYSTEM-MIB;
      	
      	      ssh		OBJECT IDENTIFIER ::= {accessSecurity 1}
      	      
      	    sshEnable OBJECT-TYPE
	          SYNTAX  INTEGER{
	      		disable(0), 						
	      		enable(1)						
	      		}
	            MAX-ACCESS  read-write
	            STATUS  current
	            DESCRIPTION
	                    "0. disable 
	                     1. enable"
	            ::= { ssh 1 }
	         
	         sshProtocolV1Enable OBJECT-TYPE
	          SYNTAX  INTEGER{
	      		disable(0), 						
	      		enable(1)						
	      		}
	            MAX-ACCESS  read-write
	            STATUS  current
	            DESCRIPTION
	                    "0. disable 
	                     1. enable"
	            ::= { ssh 2 }
	            
	        sshProtocolV2Enable OBJECT-TYPE
	          SYNTAX  INTEGER{
	      		disable(0), 						
	      		enable(1)						
	      		}
	            MAX-ACCESS  read-write
	            STATUS  current
	            DESCRIPTION
	                    "0. disable 
	                     1. enable"
	            ::= { ssh 3 }
    
    			sshQuietPeriod OBJECT-TYPE
          SYNTAX  INTEGER
            MAX-ACCESS  read-write
            STATUS  current
            DESCRIPTION
                    "quiet period(1-999 second)"
            ::= { ssh 4 }  
            
          sshMaxConnections OBJECT-TYPE
          SYNTAX  INTEGER
            MAX-ACCESS  read-write
            STATUS  current
            DESCRIPTION
                    "max connection(1-5)"
            ::= { ssh 5 } 
             	
          END
