-- Performance spanning tree port config
-- modify history: not change
--    

TLSG5412F-SPANNING-TREE-PORTCFG-MIB DEFINITIONS ::= BEGIN

           	 
  					IMPORTS
              OBJECT-TYPE
          	  	         	FROM SNMPv2-SMI
              		spanningTreePortConfig          
          	  	          	FROM  TLSG5412F-SPANNING-TREE-MIB;
           stpPortConfig  	OBJECT IDENTIFIER ::= {spanningTreePortConfig 1}
           
           stpPortConfigTable OBJECT-TYPE
              SYNTAX  SEQUENCE OF STPPORTCONFIGENTRY
              MAX-ACCESS  not-accessible
              STATUS  current
              DESCRIPTION
                      "Here you can configure the parameters of the ports for 
                      comparison in the CIST and the common parameters of all 
                      Instances. And you can view the status of the ports in the 
                      CIST. CIST (Common and Internal Spanning Tree) is the spanning 
                      tree in a switched network, connecting all devices in the network."
              ::= { stpPortConfig 1 }

          stpPortConfigEntry OBJECT-TYPE
              SYNTAX  STPPORTCONFIGENTRY
              MAX-ACCESS  not-accessible
              STATUS  current
              DESCRIPTION
                      "An entry contains of the information of a port."
              INDEX   { stpPortNumber }
              ::= { stpPortConfigTable 1 }
      
          STPPORTCONFIGENTRY ::=
              SEQUENCE {
              		stpPortNumber
              				INTEGER,
                  stpPortEnable
                      INTEGER,
                  stpPortPRI
                      INTEGER,
                  stpPortExPathCost
                  		INTEGER,
                  stpPortInPathCost
                  		INTEGER,
                  stpEdgePortStatus
                  		INTEGER,
                  stpPointToPointStatus
                  		INTEGER,
                  stpPortMCheck
                  		INTEGER,
                  stpPortStpVersion
                  		INTEGER,
                  stpPortRole
                  		INTEGER,
                  stpPortStatus
                  		INTEGER,
                  stpPortLag
                  		OCTET STRING (SIZE (0..255))
              }
          stpPortNumber OBJECT-TYPE
          		SYNTAX  INTEGER 
              MAX-ACCESS  read-only
              STATUS  current
              DESCRIPTION
                      "Displays the port number of the switch."
              ::= { stpPortConfigEntry 1 }
                     
          stpPortEnable OBJECT-TYPE
              SYNTAX  INTEGER{
	      							disable(0), 				--Disable
	      							enable(1),						--Enable
	      							errPort(2)						--ErrPort
	      							}
              MAX-ACCESS  read-write
              STATUS  current
              DESCRIPTION
                      "Select Enable /Disable STP function for the desired port.
                      0. Disable
                      1. Enable
                      2. ErrPort"
              ::= { stpPortConfigEntry 2 }
              
          stpPortPRI OBJECT-TYPE
                SYNTAX  INTEGER(0..240)
              MAX-ACCESS  read-create
              STATUS  current
              DESCRIPTION
                      "Enter a value from 0 to 240 divisible by 16. Port priority 
                      is an important criterion on determining the root port. 
                      In the same condition, the port with the highest priority will be 
                      chosen as the root port. The lower value has the higher priority."
              ::= { stpPortConfigEntry 3 }
             
          stpPortExPathCost OBJECT-TYPE
              SYNTAX  INTEGER (0..2000000)
              MAX-ACCESS  read-write
              STATUS  current
              DESCRIPTION
                      "ExPath Cost is used to choose the path and calculate the path costs 
                      of ports in different MST regions. It is an important criterion on 
                      determining the root port. The lower value has the higher priority.
                      automatic when value is zero.
                      Make sure that Path Cost ranges from 0 to 2000000."
              ::= { stpPortConfigEntry 4 }
              
     		 stpPortInPathCost OBJECT-TYPE
              SYNTAX  INTEGER (0..2000000)
              MAX-ACCESS  read-write
              STATUS  current
              DESCRIPTION
                     "InPath Cost is used to choose the path and calculate the path costs 
                     of ports in an MST region. It is an important criterion on determining 
                     the root port. The lower value has the higher priority.
                     Make sure that Path Cost ranges from 0 to 2000000."
              ::= { stpPortConfigEntry 5 }
              
         stpEdgePortStatus OBJECT-TYPE
              SYNTAX  INTEGER{
	      							disable(0), 				--Disable
	      							enable(1)						--Enable
	      							}
              MAX-ACCESS  read-write
              STATUS  current
              DESCRIPTION
                      "Select Enable/Disable Edge Port. The edge port can transit 
                      its state from blocking to forwarding rapidly without waiting 
                      for forward delay.
                      0. Disable
                      1. Enable"
              ::= { stpPortConfigEntry 6 }
              
        stpPointToPointStatus OBJECT-TYPE
		        SYNTAX  INTEGER{
		  							auto(0), 						--auto
		  							force-enable(1),		--force enable
		  							force-disable(2)		--force disable
		  							}
		        MAX-ACCESS  read-write
		        STATUS  current
		        DESCRIPTION
		                "Select the P2P link status. If the two ports in the P2P link are 
		                root port or designated port, they can transit their states to 
		                forwarding rapidly to reduce the unnecessary forward delay.
		                0. auto
		                1. force enable
		                2. force disable"
		        ::= { stpPortConfigEntry 7 }
		        
		    stpPortMCheck OBJECT-TYPE
              SYNTAX  INTEGER{
	      							unChange(0), 				--unChange
	      							enable(1)						--Enable
	      							}
              MAX-ACCESS  read-write
              STATUS  current
              DESCRIPTION
                     "Select Enable to perform MCheck operation on the port. Unchange means no MCheck operation.
                     0.	unChange
                     1.	enable"
              ::= { stpPortConfigEntry 8 }
              
         stpPortStpVersion OBJECT-TYPE
              SYNTAX  INTEGER{
	      							stp(1), 				--stp
	      							rstp(2),				--rstp
	      							mstp(3)					--mstp
	      							}
              MAX-ACCESS  read-only
              STATUS  current
              DESCRIPTION
                       "Displays the STP version of the port.
                       1.	stp
                       2.	rstp
                       3.	mstp"
              ::= { stpPortConfigEntry 9 }
              
        stpPortRole OBJECT-TYPE
		        SYNTAX  INTEGER{
		  							disabled(1), 				--Disable
		  							alternate(2),				--Alternate
		  							backup(3),					--Backup
		  							designated(4),			--Designated
		  							root(5),						--root
		  							master(6)						--Master
		  							}
		        MAX-ACCESS  read-only
		        STATUS  current
		        DESCRIPTION
		                "Displays the role of the port played in the STP Instance.
		               	1.Disable:Indicates the port that is not participating in the STP.
		                2.Alternate:Indicates the port that can be a backup port of a root 
		                	or master port.
		                3.Backup:Indicates the port that is the backup port of a designated 
		                	port. 
		                4.Designated:Indicates the port that forwards packets to a downstream 
		                	network segment or switch.
		                5.root:Indicates the port that has the lowest path cost from this bridge 
		                	to the Root Bridge and forwards packets to the root. 
		                6.Master:Indicates the port that connects a MST region to the common root. 
		                	The path from the master port to the common root is the shortest path 
		                	between this MST region and the common root."
		        ::= { stpPortConfigEntry 10 }
		        
		    stpPortStatus OBJECT-TYPE
		        SYNTAX  INTEGER{
		  							disconnected(1), 		--Disconnected
		  							blocking(2),				--Blocking
		  							learning(3),				--Learning
		  							forwarding(4)				--Forwarding
		  							}
		        MAX-ACCESS  read-only
		        STATUS  current
		        DESCRIPTION
		                "Displays the working status of the port.
		                1.Disconnected:In this status the port is not participating in the STP.
		                2.Blocking:In this status the port can only receive BPDU packets.
		                3.Learning:In this status the port can receive/send BPDU packets and 
		                	learn MAC address. 
		                4.Forwarding:In this status the port can receive/forward data, 
		                	receive/send BPDU packets as well as learn MAC address. "
		        ::= { stpPortConfigEntry 11 }
		        
		      stpPortLag OBJECT-TYPE
          		SYNTAX  OCTET STRING (SIZE (0..255))
              MAX-ACCESS  read-only
              STATUS  current
              DESCRIPTION
                    "Displays the LAG number which the port belongs to."
              ::= { stpPortConfigEntry 12 }
      	
      END
