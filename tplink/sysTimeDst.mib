TLSG5412F-DST-MIB DEFINITIONS ::= BEGIN

	IMPORTS
		OBJECT-TYPE
					FROM SNMPv2-SMI
		dstConfig		
					FROM TLSG5412F-SYSTIME-MIB;

	dstStatus	OBJECT-TYPE
		SYNTAX INTEGER
			{   
				disabled(0), 
				predefined(1),
				recurring(2),
				date(3)
			}
		MAX-ACCESS read-write
		STATUS	current
		DESCRIPTION
			"An indication of whether the summertime feature
             is disabled or is in date, predefined or recurring mode on this 
             device.
             When this object is set to date,then the dstOffset, 
             dstDateStart, dstDateEnd objects work effectively 
             and the summertime feature works one-off.
             When this object is set to predefined, the the dstRegionSelected
             object works effectively and the summertime feature 
             works recurrently.
             when this object is set to recurring, then the dstOffset, 
             dstRecurringStart, dstRecurrentEnd objects work effectively 
             and the summertime feature work recurrently." 
		DEFVAL { disabled } 
	::= {dstConfig 1}
	
	
	dstOffset	OBJECT-TYPE
		SYNTAX	INTEGER (1..1440)  --1440 minutes equals 24 hours
		UNITS	"Minutes"
		MAX-ACCESS	read-write
		STATUS		current
		DESCRIPTION
			"The value of this object indicates number of minutes to add
             or to subtract during summertime.This object is not instantiated
             when dstStatus object is set to disable." 
        DEFVAL { 60 }
	::= { dstConfig 2}	  
	
	dstDate	OBJECT IDENTIFIER	::= { dstConfig 3 }
	dstPredefined	OBJECT IDENTIFIER ::= {dstConfig 4 }
	dstRecurring	OBJECT IDENTIFIER ::= {dstConfig 5 }
	
	--**************
	--	dstDate
	--************** 
	dstDateStart	OBJECT-TYPE
	   SYNTAX	OCTET STRING (SIZE (4))
	   MAX-ACCESS  read-write
	   STATUS      current
	   DESCRIPTION
			"Indicates summertime starts at this time this year.
             octets    contents     range 
                 1         month       1..12
                                       where January = 1 December = 12
                 2         monthDay    1..31,                
                 3         hour        0..23
                 4         min         0..59

             For example, the Feb first at 13:30pm
             should be given as 02 01 0e 1e
             For the dec tenth at 1:20am should be
             given as 0c 0a 01 14
             This object is not instantiated when
             dstStatus object is not set to date."
	::= { dstDate 1 }

	dstDateEnd	OBJECT-TYPE
	   SYNTAX	OCTET STRING  (SIZE (4))
	   MAX-ACCESS  read-write
	   STATUS      current
	   DESCRIPTION
			 "Indicates summertime starts at this time this year.
             octets    contents     range 
                 1         month       1..12
                                       where January = 1 December = 12
                 2         monthDay    1..31,                 
                 3         hour        0..23
                 4         min         0..59

             For example, the February third at 3:30am
             should be given as 02 03 03 1e
             For the May first at 1:20am  should
             be given as 05 01 01 14             
             This object is not instantiated when
             dstStatus object is not set to date."
	::= { dstDate 2 } 
	
	--***************
	--	dstPredefined
	--***************
	dstRegionSelected	OBJECT-TYPE
		SYNTAX	INTEGER
			{   
				none(0),
				usa(1),
				australia(2),
				europe(3),
				new-Zealand(4)
			}
		MAX-ACCESS	read-write
		STATUS		current
		DESCRIPTION
			"Indicates the region selected when the dstStatus object is set to predefined.
			 	1.none indicates the dstMode object is not set to predefined.
			 	2.USA indicates the summertime is starts from the second Sunday in March at 02:00am
			 and ends to the first Sunday in November at 02:00am
			 	3.Australia indicates the summertime is starts from the first Sunday in October at 02:00am
			 and ends to the first Sunday in April at 03:00am next year
			 	4.Europe indicates the summertime is starts from the last Sunday in March at 01:00am
			 and ends to last Sunday in October at 01:00am.
			 	5.New Zealand indicates the summertime is start from the last Sunday in September at 02:00am
			 and ends to the first Sunday in April at 03:00am next year"
			 
	::= {dstPredefined 1}	                                            
	
	--****************
	--	dstRecurring
	--****************
	dstRecurringStart	OBJECT-TYPE
   		SYNTAX	OCTET STRING  (SIZE (6))
   		MAX-ACCESS  read-write
   		STATUS      current
   		DESCRIPTION
            "Indicates summertime starts at this time every year.
             octets    contents     range
             1         week        1..4,ff 
             					   where last = ff
             2-3       day         0..6
                                   where Sunday = 0 Saturday = 6
             4         month       1..12
                                   where January = 1 December = 12
             5         hour        0..23
             6         min         0..59

             For example, the first Monday in Feb at 13:30pm
             should be given as 01 00 01 02 0e 1e
             For the last Tuesday in Dec at 1:20am should be
             given as ff 00 02 0c 01 14
             This object is not instantiated when
             dstStatus object is not set to recurring." 
	::= {dstRecurring 1}
	   
	dstRecurringEnd	OBJECT-TYPE
   		SYNTAX	OCTET STRING  (SIZE (6))
   		MAX-ACCESS  read-write
   		STATUS      current
   		DESCRIPTION
            "Indicates summertime starts at this time every year.
           	 octets    contents     range
             1         week        1..4,ff 
             					   where last = ff
             2-3       day         0..6
                                   where Sunday = 0 Saturday = 6
             4         month       1..12
                                   where January = 1 December = 12
             5         hour        0..23
             6         min         0..59

             For example, the third Friday in February at 3:30am
             should be given as 03 00 05 02 03 1e
             For the first Tuesday in May at 1:20am  should
             be given as 01 00 02 05 01 14
             This object is not instantiated when
             dstStatus object is not set to recurring." 
	::= {dstRecurring 2}    
	   
	END
