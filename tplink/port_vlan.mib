-- Performance vlan config
-- modify history: not change
--    

TLSG5412F-PORT-VLAN-MIB DEFINITIONS ::= BEGIN

          IMPORTS
              RowStatus       	 
  					FROM SNMPv2-TC
              OBJECT-TYPE,MODULE-IDENTITY
          	  	         	FROM SNMPv2-SMI
              	portVlan	          
          	  	          	FROM  TLSG5412F-VLAN-MIB;
          	  	          	
          	portVlanNotifications OBJECT IDENTIFIER ::={portVlan 2}
          	  	          	        	
          	vlanTableCreate NOTIFICATION-TYPE
    			OBJECTS {
                        portVlanId,                        
                        }
    			STATUS          current
    			DESCRIPTION
        			""
   			::= { portVlanNotifications 1}              
   			
   			--vlanTableChanges NOTIFICATION-TYPE
    		--	OBJECTS { 
    		--			portVlanId,
    		--			}
    		--	STATUS          current
    		--	DESCRIPTION
        	--		""
   			--::= { portVlanNotifications 2}  	          	        	
       		
       		portVlanConfig MODULE-IDENTITY  
			    LAST-UPDATED    "200812160000Z"
			    ORGANIZATION    "TPLINK"
			    CONTACT-INFO		"www.tplink.com.cn"
			    DESCRIPTION
			            "VLAN (Virtual Local Area Network) technology is developed for 
			            the switch to divide the LAN into multiple logical LANs flexibly.
			            Hosts in the same VLAN can communicate with each other, regardless
			            of their physical locations. VLAN can enhance performance by conserving
			            bandwidth, and improve security by limiting traffic to specific domains."
			    REVISION        "200908030000Z"
			    DESCRIPTION
					"Initial version of this MIB module."
			    ::= { portVlan 1 }      	      
      	   

          
          vlanPortConfigTable OBJECT-TYPE
              SYNTAX  SEQUENCE OF VLANPORTCONFIGENTRY
              MAX-ACCESS  not-accessible
              STATUS  current
              DESCRIPTION
                   "The switch provides three Link Types for the ports. Usually,
                   the ACCESS port is to connect to the terminal hosts, such as 
			             PC and Server; the TRUNK port is to connect to the switch; 
			             the GENERAL port can connect to the terminal hosts or the 
			             switch also."
              ::= { portVlanConfig 1 }

          vlanPortConifgEntry OBJECT-TYPE
              SYNTAX  VLANPORTCONFIGENTRY
              MAX-ACCESS  not-accessible
              STATUS  current
              DESCRIPTION
                      "An entry contains of the information of a port parameter."
              INDEX   { vlanPortNumber }
              ::= { vlanPortConfigTable 1 }
      
          VLANPORTCONFIGENTRY ::=
              SEQUENCE {
                 	vlanPortNumber
              				INTEGER,
              		vlanPortType
              				INTEGER,
              		vlanPortPvid
              				INTEGER,
              		vlanPortLag
              			OCTET STRING (SIZE (0..255))
              				
              }
              
           vlanPortNumber OBJECT-TYPE
            	SYNTAX  INTEGER  
              MAX-ACCESS  read-only
              STATUS  current
              DESCRIPTION
                      "Displays the port number."
              ::= { vlanPortConifgEntry 1 }
                     
          vlanPortType OBJECT-TYPE
          		SYNTAX  INTEGER{
	      			access(0), 					--ACCESS
	      			trunk(1),						--TRUNK
	      			general(2)					--GENERAL
	      			}
              MAX-ACCESS  read-write
              STATUS  current
              DESCRIPTION
              					"0.ACCESS:The ACCESS port can be added in a single VLAN,and the 
              					egress rule of the port is UNTAG. The PVID is same as the current 
              					VLAN ID. If the current VLAN is deleted,the PVID will be set to 1 
              					by default.
              					1.TRUNK:The TRUNK port can be added in multiple VLANs, and the
              					egress rule of the port is TAG. The PVID can be set as the VID 
              					number of any VLAN the port belongs to.
              					2.GENERAL:The GENERAL port can be added in multiple VLANs and set 
              					various egress rules according to the different VLANs. The default 
              					egress rule is UNTAG. The PVID can be set as the VID number of any 
              			 		VLAN the port belongs to."
              ::= { vlanPortConifgEntry 2 }
              
              vlanPortPvid OBJECT-TYPE
          		SYNTAX  INTEGER(1..4094)
              MAX-ACCESS  read-write
              STATUS  current
              DESCRIPTION
                      	"Enter the PVID number of the port, 1-4094"
              ::= { vlanPortConifgEntry 3 }
              
            vlanPortLag OBJECT-TYPE
          		SYNTAX  OCTET STRING (SIZE (0..255))
              MAX-ACCESS  read-only
              STATUS  current
              DESCRIPTION
                      		"Displays the LAG to which the port belongs."
              ::= { vlanPortConifgEntry 4 }
          
          
           vlanConfigTable OBJECT-TYPE
              SYNTAX  SEQUENCE OF PORTVLANCONFIGENTRY
              MAX-ACCESS  not-accessible
              STATUS  current
              DESCRIPTION
                      "Here you can view and modify the VLAN Table."
              ::= { portVlanConfig 2 }

          vlanConfigEntry OBJECT-TYPE
              SYNTAX  PORTVLANCONFIGENTRY
              MAX-ACCESS  not-accessible
              STATUS  current
              DESCRIPTION
                      "An entry contains of the information of a vlan."
              INDEX   { portVlanId }
              ::= { vlanConfigTable 1 }
      
          PORTVLANCONFIGENTRY ::=
              SEQUENCE {
                  portVlanId
                      INTEGER, 
                  portVlanDescription 
                  		OCTET STRING (SIZE (0..255)), 
                  vlanTagPortMemberAdd
                  		OCTET STRING (SIZE (0..255)), 
                  vlanUntagPortMemberAdd
                  		OCTET STRING (SIZE (0..255)), 
                  vlanPortMemberRemove
                	  OCTET STRING (SIZE (0..255)), 
                  portVlanStatus
                      RowStatus
              }
              
          portVlanId OBJECT-TYPE
              SYNTAX  INTEGER(1..4094)  
              MAX-ACCESS  read-create
              STATUS  current
              DESCRIPTION
                      "Enter the ID number of VLAN,2-4094."
              ::= { vlanConfigEntry 1 }
          
          portVlanDescription OBJECT-TYPE
              SYNTAX OCTET STRING (SIZE (0..255)) 
              MAX-ACCESS  read-create
              STATUS  current
              DESCRIPTION
                      "Give a description to the VLAN for identification,1-16 characters"
              ::= { vlanConfigEntry 2 }
              
          vlanTagPortMemberAdd OBJECT-TYPE
		          SYNTAX OCTET STRING (SIZE (0..255)) 
		          MAX-ACCESS  read-write
		          STATUS  current
		          DESCRIPTION
		                  "Enter the desired port to be a tag member of VLAN,The format of input 
		                  port number should be like '1, 3, 4-7, 11'.
		                  tag:All packets forwarded by the port are tagged. The packets contain 
		                  VLAN information."
		          ::= { vlanConfigEntry 3 }
		          
         vlanUntagPortMemberAdd OBJECT-TYPE
		          SYNTAX OCTET STRING (SIZE (0..255)) 
		          MAX-ACCESS  read-write
		          STATUS  current
		          DESCRIPTION
		                  "Enter the desired port to be a untag member of VLAN,The format of input 
		                  port number should be like '1, 3, 4-7, 11'.
		                  untag:Packets forwarded by the port are untagged."
		          ::= { vlanConfigEntry 4 }
		     vlanPortMemberRemove OBJECT-TYPE
		          SYNTAX OCTET STRING (SIZE (0..255)) 
		          MAX-ACCESS  read-write
		          STATUS  current
		          DESCRIPTION
		                  "Remove port member of vlan,The format of input port number should be like 
		                  '1, 3, 4-7, 11'."
		          ::= { vlanConfigEntry 5 }
                    
         portVlanStatus OBJECT-TYPE
              SYNTAX  RowStatus
              MAX-ACCESS  read-create
              STATUS  current
              DESCRIPTION
                      "the following two values are states:
                     these values may be read or written
                     active(1),
                     notInService(2),

                     the following value is a state:
                     this value may be read, but not written
                     notReady(3),

                     the following three values are
                     actions: these values may be written,
                     but are never read
                     createAndGo(4),
                     createAndWait(5),
                     destroy(6)"
              ::= { vlanConfigEntry 6 }

      	
          END
