TLSG5412F-L2SWITCH-MIB DEFINITIONS ::= BEGIN
		IMPORTS
		   
		   MODULE-IDENTITY
			  	         	FROM SNMPv2-SMI
		    tlsg5412f	          
			  	          	FROM TPLINK; 
          	  	          
          	 
		l2switch MODULE-IDENTITY
		LAST-UPDATED    "200908270000Z"
		ORGANIZATION    "TPLINK"
		CONTACT-INFO		"www.tplink.com.cn"
		DESCRIPTION			"l2Switch Private MIB."
		REVISION        "200908270000Z"
		DESCRIPTION			"Initial version of this MIB module."
		::= { tlsg5412f 2 }
		
		l2PortManage   	OBJECT IDENTIFIER ::= {l2switch 1}
		etherchannel	OBJECT IDENTIFIER ::= {l2switch 2}
		l2BridgeManage  OBJECT IDENTIFIER::= { l2switch 3 }
	    
END
