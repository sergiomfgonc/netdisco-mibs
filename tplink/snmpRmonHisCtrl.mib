TLSG5412F-SNMPRMONHISOTRYCTRL-MIB DEFINITIONS ::= BEGIN

          IMPORTS
             
            RowStatus       	 
  					FROM SNMPv2-TC
            OBJECT-TYPE,TimeTicks,Counter32
          	  	         	FROM SNMPv2-SMI
            snmpRmonHistoryCtrl	          
          	  	          	FROM TLSG5412F-SNMPRMON-MIB; 
          	  	          
          	 
	 snmpRmonHistoryCtrlTable OBJECT-TYPE
	    SYNTAX  SEQUENCE OF SNMPRMONHISOTRYCTRLENTRY
	    MAX-ACCESS not-accessible
	    STATUS  current
	    DESCRIPTION
	    		"A list of SNMP RMON history control entries."
	    ::= {snmpRmonHistoryCtrl 1}

	 snmpRmonHistoryCtrlEntry OBJECT-TYPE
	    SYNTAX  SNMPRMONHISOTRYCTRLENTRY
	    MAX-ACCESS  not-accessible
	    STATUS  current
	    DESCRIPTION
                      "  History Group is one of the commonly used RMON (Remote Monitoring) Groups. After a 
                      history group is configured, the switch collects network statistics information 
                      periodically, based on which the management station can monitor network effectively."
            INDEX   { snmpRmonHistoryCtrlIndex }
            ::= { snmpRmonHistoryCtrlTable 1 }
      
          SNMPRMONHISOTRYCTRLENTRY ::=
              SEQUENCE {
                  snmpRmonHistoryCtrlIndex
                      INTEGER, 
                  snmpRmonHistoryCtrlSourcePort
                      INTEGER,
                  snmpRmonHistoryCtrlInterval
                      INTEGER,
                  snmpRmonHistoryCtrlOwner
                      OCTET STRING (SIZE (0..16)),
                  snmpRmonHistoryCtrlStatus
                      INTEGER
              }
         
         snmpRmonHistoryCtrlIndex OBJECT-TYPE
         	SYNTAX		INTEGER
         	MAX-ACCESS	read-only
         	STATUS		current
         	DESCRIPTION	
         		"The index number of the entry."
         	::={snmpRmonHistoryCtrlEntry 1}
         	
         snmpRmonHistoryCtrlSourcePort OBJECT-TYPE
         	SYNTAX		INTEGER
         	MAX-ACCESS	read-write
         	STATUS		current
         	DESCRIPTION	
         		"The port from which the history samples were taken."
         	::={snmpRmonHistoryCtrlEntry 2}
         
         snmpRmonHistoryCtrlInterval OBJECT-TYPE
         	SYNTAX		INTEGER
         	MAX-ACCESS	read-write
         	STATUS		current
         	DESCRIPTION	
 			" The interval to take samplings from the port.
 			10sec-3600sec."
         	::={snmpRmonHistoryCtrlEntry 3}	
         
         snmpRmonHistoryCtrlOwner OBJECT-TYPE
         	SYNTAX		OCTET STRING (SIZE (0..16))
         	MAX-ACCESS	read-write
         	STATUS		current
         	DESCRIPTION	
         		"The name of the device or user that defined the entry."
         	::={snmpRmonHistoryCtrlEntry 4}
         
         snmpRmonHistoryCtrlStatus OBJECT-TYPE
         	SYNTAX  INTEGER{
	      		disable(0), 					
	      		enable(1)					
	      		}
              	MAX-ACCESS  read-write
              	STATUS  current
              	DESCRIPTION
                      "Enable/Disable the corresponding sampling entry.
                       disable(0), disable the history entry.					
	      	       enable(1), enable the history entry."
         	::={snmpRmonHistoryCtrlEntry 5}

  
  
  	snmpRmonHistoryDataTable OBJECT-TYPE
	    SYNTAX  SEQUENCE OF SNMPRMONHISOTRYDATAENTRY
	    MAX-ACCESS not-accessible
	    STATUS  current
	    DESCRIPTION
	    		"A list of SNMP RMON history data entries."
	    ::= {snmpRmonHistoryCtrl 2}

	 snmpRmonHistoryDataEntry OBJECT-TYPE
	    SYNTAX  SNMPRMONHISOTRYDATAENTRY
	    MAX-ACCESS  not-accessible
	    STATUS  current
	    DESCRIPTION
                      "Contains of the history data for a control entry"
            INDEX   { snmpRmonHistoryDataIndex }
            ::= { snmpRmonHistoryDataTable 1 }
      
          SNMPRMONHISOTRYDATAENTRY ::=
              SEQUENCE {
                 snmpRmonHistoryDataIndex
                      INTEGER, 
                 snmpRmonHistoryDataSampleIndex
                      INTEGER,
                 snmpRmonHistoryDataIntervalStart
                      TimeTicks,
                 snmpRmonHistoryDataDropEvents
                      Counter32,
                 snmpRmonHistoryDataOctets
                      Counter32,
                 snmpRmonHistoryDataPkts
                      Counter32,
                 snmpRmonHistoryDataBroadcastPkts
                      Counter32,
                 snmpRmonHistoryDataMulticastPkts
                      Counter32,
                 snmpRmonHistoryDataCRCAlignErrors
                      Counter32,
                 snmpRmonHistoryDataUndersizePkts
                      Counter32,
                 snmpRmonHistoryDataOversizePkts
                      Counter32,
                 snmpRmonHistoryDataFragments
                      Counter32,
                 snmpRmonHistoryDataJabbers
                      Counter32,
                 snmpRmonHistoryDataCollisions
                      Counter32,
                  snmpRmonHistoryDataUtilization
                      INTEGER
              }
       
       
	 snmpRmonHistoryDataIndex OBJECT-TYPE
	     SYNTAX     INTEGER (1..65535)
	     MAX-ACCESS read-only
	     STATUS     current
	     DESCRIPTION
	         "index"
	     ::= { snmpRmonHistoryDataEntry 1 }

	 snmpRmonHistoryDataSampleIndex OBJECT-TYPE
	     SYNTAX     INTEGER (1..2147483647)
	     MAX-ACCESS read-only
	     STATUS     current
	     DESCRIPTION
	         "An index that uniquely identifies the particular
 		sample this entry represents among all samples
 		associated with the same historyControlEntry.
 		This index starts at 1 and increases by one
 		as each new sample is taken."
	     ::= { snmpRmonHistoryDataEntry 2 }

	 snmpRmonHistoryDataIntervalStart OBJECT-TYPE
	     SYNTAX     TimeTicks
	     MAX-ACCESS read-only
	     STATUS     current
	     DESCRIPTION
	        "  The value of sysUpTime at the start of the interval
 		over which this sample was measured.  If the probe
 		keeps track of the time of day, it should start
 		the first sample of the history at a time such that
 		when the next hour of the day begins, a sample is
 		started at that instant.  Note that following this
 		rule may require the probe to delay collecting the
 		first sample of the history, as each sample must be
 		of the same interval.  Also note that the sample which
 		is currently being collected is not accessible in this
 		table until the end of its interval."
	     ::= { snmpRmonHistoryDataEntry 3 }
	
	 snmpRmonHistoryDataDropEvents OBJECT-TYPE
	     SYNTAX     Counter32
	     MAX-ACCESS read-only
	     STATUS     current
	     DESCRIPTION
	        "  The total number of events in which packets
 		were dropped by the probe due to lack of resources
 		during this sampling interval.  Note that this number
 		is not necessarily the number of packets dropped, it
 		is just the number of times this condition has been
 		detected."
	     ::= { snmpRmonHistoryDataEntry 4 }
	
	 snmpRmonHistoryDataOctets OBJECT-TYPE
	     SYNTAX     Counter32
	     UNITS      "Octets"
	     MAX-ACCESS read-only
	     STATUS     current
	     DESCRIPTION
	        "  The total number of octets of data (including
 		those in bad packets) received on the
 		network (excluding framing bits but including
 		FCS octets)"
	     ::= { snmpRmonHistoryDataEntry 5 }
	
	 snmpRmonHistoryDataPkts OBJECT-TYPE
	     SYNTAX     Counter32
	     UNITS      "Packets"
	     MAX-ACCESS read-only
	     STATUS     current
	     DESCRIPTION
	        "    The number of packets (including bad packets)
 		received during this sampling interval."
	     ::= { snmpRmonHistoryDataEntry 6 }
	
	 snmpRmonHistoryDataBroadcastPkts OBJECT-TYPE
	     SYNTAX     Counter32
	     UNITS      "Packets"
	     MAX-ACCESS read-only
	     STATUS     current
	     DESCRIPTION
	        "  The number of good packets received during this
 		sampling interval that were directed to the
 		broadcast address."
	     ::= { snmpRmonHistoryDataEntry 7 }
	
	 snmpRmonHistoryDataMulticastPkts OBJECT-TYPE
	     SYNTAX     Counter32
	     UNITS      "Packets"
	     MAX-ACCESS read-only
	     STATUS     current
	     DESCRIPTION
	        "  The number of good packets received during this
 		sampling interval that were directed to the
 		broadcast address."
	     ::= { snmpRmonHistoryDataEntry 8 }
	
	 snmpRmonHistoryDataCRCAlignErrors OBJECT-TYPE
	     SYNTAX     Counter32
	     UNITS      "Packets"
	     MAX-ACCESS read-only
	     STATUS     current
	     DESCRIPTION
	        "  The number of packets received during this sampling
 		interval that had a length (excluding framing bits
 		but including FCS octets) between 64 and 1518
 		octets, inclusive, but had either a bad Frame Check
 		Sequence (FCS) with an integral number of octets
 		(FCS Error) or a bad FCS with a non-integral number
 		of octets (Alignment Error)."
	     ::= { snmpRmonHistoryDataEntry 9 }
	
	 snmpRmonHistoryDataUndersizePkts OBJECT-TYPE
	     SYNTAX     Counter32
	     UNITS      "Packets"
	     MAX-ACCESS read-only
	     STATUS     current
	     DESCRIPTION
	        "  The number of packets received during this
 		sampling interval that were less than 64 octets
 		long (excluding framing bits but including FCS
 		octets) and were otherwise well formed."
	     ::= { snmpRmonHistoryDataEntry 10 }
	
	 snmpRmonHistoryDataOversizePkts OBJECT-TYPE
	     SYNTAX     Counter32
	     UNITS      "Packets"
	     MAX-ACCESS read-only
	     STATUS     current
	     DESCRIPTION
	        "  The number of packets received during this
 		sampling interval that were longer than 1518
 		octets (excluding framing bits but including
 		FCS octets) but were otherwise well formed."
	     ::= { snmpRmonHistoryDataEntry 11 }
	
	 snmpRmonHistoryDataFragments OBJECT-TYPE
	     SYNTAX     Counter32
	     UNITS      "Packets"
	     MAX-ACCESS read-only
	     STATUS     current
	     DESCRIPTION
	        "  The total number of packets received during this
 		sampling interval that were less than 64 octets in
 		length (excluding framing bits but including FCS
 		octets) had either a bad Frame Check Sequence (FCS)
 		with an integral number of octets (FCS Error) or a bad
 		FCS with a non-integral number of octets (Alignment
 		Error)."
	     ::= { snmpRmonHistoryDataEntry 12 }
	
	 snmpRmonHistoryDataJabbers OBJECT-TYPE
	     SYNTAX     Counter32
	     UNITS      "Packets"
	     MAX-ACCESS read-only
	     STATUS     current
	     DESCRIPTION
	        "  The number of packets received during this
 		sampling interval that were longer than 1518 octets
 		(excluding framing bits but including FCS octets),
 		and  had either a bad Frame Check Sequence (FCS)
 		with an integral number of octets (FCS Error) or
 		a bad FCS with a non-integral number of octets
 		(Alignment Error)."
	     ::= { snmpRmonHistoryDataEntry 13 }
	
	 snmpRmonHistoryDataCollisions OBJECT-TYPE
	     SYNTAX     Counter32
	     UNITS      "Collisions"
	     MAX-ACCESS read-only
	     STATUS     current
	     DESCRIPTION
	        "  The number of collisions received during this
 		sampling interval that"
	     ::= { snmpRmonHistoryDataEntry 14 }
	
	 snmpRmonHistoryDataUtilization OBJECT-TYPE
	     SYNTAX     INTEGER (0..10000)
	     MAX-ACCESS read-only
	     STATUS     current
	     DESCRIPTION
	        "  The best estimate of the mean physical layer
 		network utilization on this interface during this
 		sampling interval, in hundredths of a percent."
	     ::= { snmpRmonHistoryDataEntry 15 }
      
          END
