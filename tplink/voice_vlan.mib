-- Performance voice vlan config
-- modify history: not change
--    

TLSG5412F-VOICE-VLAN-MIB DEFINITIONS ::= BEGIN

           	 
  					IMPORTS
  					 	RowStatus       	 
  												FROM SNMPv2-TC
              OBJECT-TYPE,MODULE-IDENTITY
          	  	         	FROM SNMPv2-SMI
             voiceVlan	          
        	  	          FROM  TLSG5412F-SERVICE-QUALITY-MIB; 
          	  	      
			    	
			 voiceVlanGlobalConfig   	OBJECT IDENTIFIER ::= {voiceVlan 1}	    	    	      
      	   
          voiceVlanGlobalEnable OBJECT-TYPE
          		SYNTAX  INTEGER{
	      											disable(0), 				--disable
	      											enable(1)						--enable
	      											}
              MAX-ACCESS  read-write
              STATUS  current
              DESCRIPTION
                      "Select Enable/Disable Voice VLAN function.
                      0. disable 
                      1. enable"
              ::= { voiceVlanGlobalConfig 1 }
              
          voiceVlanId OBJECT-TYPE
              SYNTAX  INTEGER (2..4094)
              MAX-ACCESS  read-write
              STATUS  current
              DESCRIPTION
                      "Enter the VLAN ID of the voice VLAN,2-4094."
              ::= { voiceVlanGlobalConfig 2 }
              
          voiceVlanAgingTime OBJECT-TYPE
              SYNTAX  INTEGER 
              MAX-ACCESS  read-write
              STATUS  current
              DESCRIPTION
                      "Specifies the living time of the member port in auto mode 
                      after the OUI address is aging out,1-43200 minute."
              ::= { voiceVlanGlobalConfig 3 }
                    
           voiceVlanPortConfig   	OBJECT IDENTIFIER ::= {voiceVlan 2}
           
           voiceVlanPortTable OBJECT-TYPE
              SYNTAX  SEQUENCE OF VOICEVLANPORTENTRY
              MAX-ACCESS  not-accessible
              STATUS  current
              DESCRIPTION
                      "Here you can configure the parameters of the ports in the voice VLAN.."
              ::= { voiceVlanPortConfig 1 }

          voiceVlanPortEntry OBJECT-TYPE
              SYNTAX  VOICEVLANPORTENTRY
              MAX-ACCESS  not-accessible
              STATUS  current
              DESCRIPTION
                      "An entry contains of the information of port parameter."
              INDEX   { voiceVlanPortNumber }
              ::= { voiceVlanPortTable 1 }
      
          VOICEVLANPORTENTRY ::=
              SEQUENCE {
              		voiceVlanPortNumber
              				INTEGER,
                  voiceVlanPortMode
                      INTEGER,
                  voiceVlanPortSecurity
                      INTEGER,
                  voiceVlanPortStatus
                  		INTEGER,
                  voiceVlanPortLag
                  		OCTET STRING (SIZE (0..255))
              }
          voiceVlanPortNumber OBJECT-TYPE
            	 SYNTAX  INTEGER  
              MAX-ACCESS  read-only
              STATUS  current
              DESCRIPTION
                      "Displays the port number of the Switch."
              ::= { voiceVlanPortEntry 1 }
                     
          voiceVlanPortMode OBJECT-TYPE
              SYNTAX  INTEGER{
	      										manual(0), 						--manual
	      										auto(1)						--Enable
	      										}
              MAX-ACCESS  read-write
              STATUS  current
              DESCRIPTION
                      "Select the mode for the port to join the voice VLAN.
                      0. manual: In this mode, you can manually add a port to the 
                      voice VLAN or remove a port from the voice VLAN
                      1. auto: In this mode, the switch automatically adds a port 
                      to the voice VLAN or removes a port from the voice VLAN by 
                      checking whether the port receives voice data or not."
              ::= { voiceVlanPortEntry 2 }
              
          voiceVlanPortSecurity OBJECT-TYPE
              SYNTAX  INTEGER{
	      										disable(0), 					--Disable
	      										enable(1)							--Enable
	      										}
              MAX-ACCESS  read-write
              STATUS  current
              DESCRIPTION
                      "Configure the security mode for forwarding packets.
                      0. disable:All packets are forwarded.
                      1. enable:Only voice data are forwarded."
              ::= { voiceVlanPortEntry 3 }
             
          voiceVlanPortStatus OBJECT-TYPE
              SYNTAX  INTEGER{
	      										inactive(0), 					--inactive
	      										active(1)							--active
	      										}
              MAX-ACCESS  read-only
              STATUS  current
              DESCRIPTION
                      "Displays the state of the port in the current voice VLAN.
                      0. inactive
                      1. active"
              ::= { voiceVlanPortEntry 4 }
              
          voiceVlanPortLag OBJECT-TYPE
          		SYNTAX  OCTET STRING (SIZE (0..255))
              MAX-ACCESS  read-only
              STATUS  current
              DESCRIPTION
                      	"Displays the LAG number which the port belongs to."
              ::= { voiceVlanPortEntry 5 } 
              
        	voiceVlanOuiConfig   	OBJECT IDENTIFIER ::= {voiceVlan 3}
        	
        	
          
           voiceVlanOuiConfigTable OBJECT-TYPE
              SYNTAX  SEQUENCE OF VOICEVLANOUICONFIGENTRY
              MAX-ACCESS  not-accessible
              STATUS  current
              DESCRIPTION
                      "The switch determines whether a received packet is a voice 
                      packet by checking its source MAC address. If the source 
                      MAC addresses of packets comply with the OUI (organizationally 
                      unique identifier) addresses configured by the system, the packets 
                      are recognized as voice packets and transmitted in voice VLAN."
              ::= { voiceVlanOuiConfig 1 }
       
          voiceVlanOuiConfigEntry OBJECT-TYPE
              SYNTAX  	VOICEVLANOUICONFIGENTRY
              MAX-ACCESS  not-accessible
              STATUS  current
              DESCRIPTION
                      "An entry contains of the information of a voice vlan oui."
              INDEX   { voiceVlanOui }
              ::= { voiceVlanOuiConfigTable 1}
      
          VOICEVLANOUICONFIGENTRY ::=
              SEQUENCE {
                  voiceVlanOui
                     OCTET STRING (SIZE (0..255)), 
                   voiceVlanOuiMask
                 		 OCTET STRING (SIZE (0..255)),
                  voiceVlanDescription
                  	OCTET STRING (SIZE (0..255)),
                  voiceVlanStatus
                      RowStatus
              }
              
          voiceVlanOui OBJECT-TYPE
              SYNTAX OCTET STRING (SIZE (0..255))
              MAX-ACCESS  read-create
              STATUS  current
              DESCRIPTION
                      "Enter the OUI address of the voice device."
              ::= { voiceVlanOuiConfigEntry 1 }
              
          voiceVlanOuiMask OBJECT-TYPE
              SYNTAX OCTET STRING (SIZE (0..255))
              MAX-ACCESS  read-create
              STATUS  current
              DESCRIPTION
                      "Enter the OUI address mask of the voice device."
              ::= { voiceVlanOuiConfigEntry 2 }
              
          voiceVlanDescription  OBJECT-TYPE
              SYNTAX  	OCTET STRING (SIZE (0..255))
              MAX-ACCESS  read-create
              STATUS  current
              DESCRIPTION
                      "Give a description to the OUI for identification,1-16 characters."
              ::= { voiceVlanOuiConfigEntry 3 }
                    
         voiceVlanStatus OBJECT-TYPE
              SYNTAX  RowStatus
              MAX-ACCESS  read-create
              STATUS  current
              DESCRIPTION
                      "the following two values are states:
                     these values may be read or written
                     active(1),
                     notInService(2),

                     the following value is a state:
                     this value may be read, but not written
                     notReady(3),

                     the following three values are
                     actions: these values may be written,
                     but are never read
                     createAndGo(4),
                     createAndWait(5),
                     destroy(6)"
              ::= { voiceVlanOuiConfigEntry 4 }
      	

              
     		
      	
          END
