-- Performance spanning tree config
-- modify history: not change
--    

 TLSG5412F-STP-BASIC-CONFIG-MIB DEFINITIONS ::= BEGIN

          IMPORTS        	 
              OBJECT-TYPE
          	  	         	FROM SNMPv2-SMI
              spanningTreeBasicConfig	          
          	  	          	FROM  TLSG5412F-SPANNING-TREE-MIB;
      	
      	      stpBasicGlobalConfig	OBJECT IDENTIFIER ::= {spanningTreeBasicConfig 1}
      	      
      	      
      	  stpEnable OBJECT-TYPE
      	  					SYNTAX  INTEGER{
      	  					disable(0), 				--disable
      	  					enable(1)						--enable
	      						}
			              MAX-ACCESS  read-write
			              STATUS  current
			              DESCRIPTION
			                      "Spanning Tree Protocol.
			                      0. disable 
			                      1. enable"
			              ::= { stpBasicGlobalConfig 1 }
              
          rstpEnable OBJECT-TYPE
				             SYNTAX  INTEGER{
				      	  					disable(0), 					--disable
				      	  					enable(1)							--enable
					      						}
				              MAX-ACCESS  read-write
				              STATUS  current
				              DESCRIPTION
				                     	"Rapid Spanning Tree Protocol.
				                     	0. disable 
				                      1. enable"
				              ::= { stpBasicGlobalConfig 2 }
              
          mstpEnable OBJECT-TYPE
				              SYNTAX  INTEGER{
				      	  					disable(0), 				--disable
				      	  					enable(1)						--enable
					      						}
				              MAX-ACCESS  read-write
				              STATUS  current
				              DESCRIPTION
				                    "Multiple Spanning Tree Protocol.
				                    0. disable 
				                    1. enable"
				              ::= { stpBasicGlobalConfig 3 }   
				            
				 stpBasicParamConfig	OBJECT IDENTIFIER ::= {spanningTreeBasicConfig 2}
          
					stpCistPri OBJECT-TYPE
				              SYNTAX  INTEGER (0..61440)
				              MAX-ACCESS  read-write
				              STATUS  current
				              DESCRIPTION
				                      "Enter a value from 0 to 61440 to specify the priority 
				                      of the switch for comparison in the CIST. CIST priority 
				                      is an important criterion on determining the root bridge. 
				                      In the same condition, the switch with the highest priority 
				                      will be chosen as the root bridge. The lower value has the 
				                      higher priority. The value could be divided exactly by 4096."
				              ::= { stpBasicParamConfig 1 }
									
				  stpHelloTime OBJECT-TYPE	
										      SYNTAX  INTEGER (1..10)
						              MAX-ACCESS  read-write
						              STATUS  current
						              DESCRIPTION
				                      "Enter a value from 1 to 10 in seconds to specify the 
				                      interval to send BPDU packets. It is used to test the 
				                      links. (stpHelloTime+1)*2<=stpAgingTime."
						              ::= { stpBasicParamConfig 2 }
						              
          stpAgingTime OBJECT-TYPE	
										      SYNTAX  INTEGER (6..40)
							            MAX-ACCESS  read-write
							            STATUS  current
							            DESCRIPTION
					                    "Enter a value from 6 to 40 in seconds to specify the 
					                    maximum time the switch can wait without receiving a 
					                    BPDU before attempting to reconfigure.
					                    (stpHelloTime+1)*2<=stpAgingTime."
								            ::= { stpBasicParamConfig 3 }
				  			
				  stpForwardDelay OBJECT-TYPE	
										      SYNTAX  INTEGER (4..30)
						              MAX-ACCESS  read-write
						              STATUS  current
						              DESCRIPTION
				                      "Enter a value from 4 to 30 in seconds to specify the 
				                      time for the port to transit its state after the network 
				                      topology is changed. stpAgingTime<=(stpForwardDelay-1)*2."
							              ::= { stpBasicParamConfig 4 }
										              
          stpHoldCount	OBJECT-TYPE
						              SYNTAX  INTEGER(1..20)
						              MAX-ACCESS  read-write
						              STATUS  current
						              DESCRIPTION
				                      "Enter a value from 1 to 20 to set the maximum number of 
				                      BPDU packets transmitted per Hello Time interval."
				              ::= { stpBasicParamConfig 5 }
              
              
          stpMaxHops OBJECT-TYPE
						              SYNTAX  INTEGER(1..40)
						              MAX-ACCESS  read-write
						              STATUS  current
						              DESCRIPTION
				                      "Enter a value from 1 to 40 to set the maximum number of 
				                      hops that occur in a specific region before the BPDU is 
				                      discarded."
              ::= { stpBasicParamConfig 6 }
              
              
              
				spannngTreeInfo OBJECT IDENTIFIER ::= {spanningTreeBasicConfig 3}
                        
         stpEnableStatus OBJECT-TYPE
              SYNTAX  INTEGER{
      	  					disable(0), 				--disable
      	  					enable(1)						--enable
	      						}
              MAX-ACCESS  read-only
              STATUS  current
              DESCRIPTION
                      "0. disable 
				               1. enable"
              ::= { spannngTreeInfo 1 }
              
          stpMode OBJECT-TYPE
              SYNTAX  INTEGER{
              				stp(1),			--stp
              				rstp(2),		--rstp
              				mstp(3)		--mstp
              				}
              MAX-ACCESS  read-only
              STATUS  current
              DESCRIPTION
                      "1.	stp
                      2.	rstp
                      3.	mstp"
              ::= { spannngTreeInfo 2 }
              
          stpLocalBridge OBJECT-TYPE
              SYNTAX  OCTET STRING (SIZE (0..255))
              MAX-ACCESS  read-only
              STATUS  current
              DESCRIPTION
                      "Local bridge."
              ::= { spannngTreeInfo 3 } 
          
          stpCISTRoot OBJECT-TYPE
           	 SYNTAX  OCTET STRING (SIZE (0..255))
           	 MAX-ACCESS  read-only
           	 STATUS  current
           	 DESCRIPTION
                    "CIST Root."
             ::= { spannngTreeInfo 4 }  
             
                  
          stpExPathCost OBJECT-TYPE
            	SYNTAX  INTEGER 
            	MAX-ACCESS  read-only
            	STATUS  current
            	DESCRIPTION
                    "External Path cost."
            ::= { spannngTreeInfo 5 } 
            
          stpRegionRoot OBJECT-TYPE
          		SYNTAX  OCTET STRING (SIZE (0..255))
              MAX-ACCESS  read-only
              STATUS  current
              DESCRIPTION
                      "Region Root."
              ::= { spannngTreeInfo 6 } 
            
        stpInPathCost OBJECT-TYPE
            	SYNTAX  INTEGER 
            	MAX-ACCESS  read-only
            	STATUS  current
            	DESCRIPTION
                    "Internal Path cost."
            ::= { spannngTreeInfo 7 } 
         
        stpDesignatedBridge OBJECT-TYPE
            	SYNTAX  OCTET STRING (SIZE (0..255))
            	MAX-ACCESS  read-only
            	STATUS  current
            	DESCRIPTION
                    "Designated Bridge."
            ::= { spannngTreeInfo 8 }
         
         stpRootPort OBJECT-TYPE
            	SYNTAX  INTEGER 
            	MAX-ACCESS  read-only
            	STATUS  current
            	DESCRIPTION
                    "RootPort."
            ::= { spannngTreeInfo 9 }  
           
         stpLastTopologyChangeTime OBJECT-TYPE
            	SYNTAX  OCTET STRING (SIZE (0..255))
            	MAX-ACCESS  read-only
            	STATUS  current
            	DESCRIPTION
                    "LastTopologyChangeTime."
            ::= { spannngTreeInfo 10 } 
            
        stpTopologyChangeCounter OBJECT-TYPE
            	SYNTAX  INTEGER 
            	MAX-ACCESS  read-only
            	STATUS  current
            	DESCRIPTION
                    "TopologyChangeCounter."
            ::= { spannngTreeInfo 11 }       	 
      	
          END
