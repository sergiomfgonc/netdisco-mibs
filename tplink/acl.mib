TLSG5412F-ACL-MIB DEFINITIONS ::= BEGIN

         IMPORTS
         		 RowStatus       	 
  												FROM SNMPv2-TC
  												
            OBJECT-TYPE,MODULE-IDENTITY
          	  	         	FROM SNMPv2-SMI
            tlsg5412f	          
          	  	          FROM TPLINK; 
          	  	          
          	 
	    acl MODULE-IDENTITY
	    LAST-UPDATED    "200908190000Z"
	    ORGANIZATION    "TPLINK"
	    CONTACT-INFO
	            " www.tplink.com.cn"
	    DESCRIPTION
	             "Private MIB for acl."
	    REVISION        "200908190000Z"
	    DESCRIPTION
	            "Initial version of this MIB module."
	    ::= { tlsg5412f 7 }
	    
			 	policyConfigure  				OBJECT IDENTIFIER ::= {acl 1}
			 	policyBindConfigure			OBJECT IDENTIFIER ::= {acl 2}
			
        -- the policy list
        
         policyTable OBJECT-TYPE
            SYNTAX  SEQUENCE OF POLICYENTRY
            MAX-ACCESS  not-accessible
            STATUS  current
            DESCRIPTION
                    "A list of policy entries.
                     Here you can add ACLs and create corresponding actions for the policy."
            ::= { policyConfigure 1 }

        policyEntry OBJECT-TYPE
            SYNTAX  POLICYENTRY
            MAX-ACCESS  not-accessible
            STATUS  current
            DESCRIPTION
                    "An entry contains of the information of policy."
            INDEX   { policyName,aclId}
            ::= { policyTable 1 }
    
        POLICYENTRY ::=
            SEQUENCE {
								policyName
										OCTET STRING (SIZE (1..255)), 
								aclId
										INTEGER,
								mirrorPort
										INTEGER,
								conditionRate
										INTEGER,
								ifExceedOperation
										INTEGER,
								redirectPort
										INTEGER,
								policyStatus
										RowStatus
            }
            
        policyName OBJECT-TYPE
            SYNTAX  OCTET STRING (SIZE (1..255))  
            MAX-ACCESS  read-only
            STATUS  current
            DESCRIPTION
                    "policy name"
            ::= { policyEntry 1 }
        
        aclId OBJECT-TYPE
            SYNTAX  INTEGER
            MAX-ACCESS  read-only
            STATUS  current
            DESCRIPTION
                    "the aclId must be existent"
            ::= { policyEntry 2 }
       
       mirrorPort OBJECT-TYPE
            SYNTAX  INTEGER
            MAX-ACCESS  read-create
            STATUS  current
            DESCRIPTION
                    "mirror the data packets in the policy to the specific port.
                     if traffic mirror doesn't work, please set it to 0"
            ::= { policyEntry 3 }
       
       conditionRate OBJECT-TYPE
            SYNTAX  INTEGER
            MAX-ACCESS  read-create
            STATUS  current
            DESCRIPTION
                    "limit the transmission rate of the data packets in the policy.(1-1000000Kbps), 
                     if traffic condition doesn't work, please set it to 0"
            ::= { policyEntry 4 }
       
      ifExceedOperation OBJECT-TYPE
            SYNTAX  INTEGER
            {
            	none(0),
            	drop(1)
            }
            MAX-ACCESS  read-create
            STATUS  current
            DESCRIPTION
                    "Specify the disposal way of the data packets those are transmitted beyond the rate.
                     (you must set the conditionRate firstly)"
            ::= { policyEntry 5 }
            
      redirectPort OBJECT-TYPE
            SYNTAX  INTEGER
            MAX-ACCESS  read-create
            STATUS  current
            DESCRIPTION
                    "Forward the data packets those match the corresponding ACL to the specific port, 
                     if you want redirect to vlan, please set it to 0"
            ::= { policyEntry 6 }
                           
       policyStatus OBJECT-TYPE
            SYNTAX  RowStatus
            MAX-ACCESS  read-create
            STATUS  current
            DESCRIPTION
                   "the following two values are states:
                   these values may be read or written
                   active(1),
                   notInService(2),

                   the following value is a state:
                   this value may be read, but not written
                   notReady(3),

                   the following three values are
                   actions: these values may be written,
                   but are never read
                   createAndGo(4),
                   createAndWait(5),
                   destroy(6)"
            ::= { policyEntry 7 }
            
       -- the policy bind list
       --policy bind to port configure
        
         polilyPortBindTable OBJECT-TYPE
            SYNTAX  SEQUENCE OF POLICYPORTBINDENTRY
            MAX-ACCESS  not-accessible
            STATUS  current
            DESCRIPTION
                    "A list of policy port binding entries.
                     Here you can bind a policy to a port. "
            ::= { policyBindConfigure 1 }

        polilyPortBindEntry OBJECT-TYPE
            SYNTAX  POLICYPORTBINDENTRY
            MAX-ACCESS  not-accessible
            STATUS  current
            DESCRIPTION
                    "An entry contains of the information of policy port binding."
            INDEX   { portBindPolicyName,port}
            ::= { polilyPortBindTable 1 }
    
        POLICYPORTBINDENTRY ::=
            SEQUENCE {
								portBindPolicyName
										OCTET STRING (SIZE (1..255)), 
								port
										INTEGER,
								policyPortBindStatus
										RowStatus
            }
            
        portBindPolicyName OBJECT-TYPE
            SYNTAX  OCTET STRING (SIZE (1..255))  
            MAX-ACCESS  read-only
            STATUS  current
            DESCRIPTION
                    "The name of the policy you want to bind.(the policy name must be existent)"
            ::= { polilyPortBindEntry 1 }
        
        port OBJECT-TYPE
            SYNTAX  INTEGER
            MAX-ACCESS  read-only
            STATUS  current
            DESCRIPTION
                    "The port that the policy bind to"
            ::= { polilyPortBindEntry 2 }
       
       policyPortBindStatus OBJECT-TYPE
            SYNTAX  RowStatus
            MAX-ACCESS  read-create
            STATUS  current
            DESCRIPTION
                   "the following two values are states:
                   these values may be read or written
                   active(1),
                   notInService(2),

                   the following value is a state:
                   this value may be read, but not written
                   notReady(3),

                   the following three values are
                   actions: these values may be written,
                   but are never read
                   createAndGo(4),
                   createAndWait(5),
                   destroy(6)"
            ::= { polilyPortBindEntry 3 }
      
       --policy bind to vlan configure
       polilyVlanBindTable OBJECT-TYPE
            SYNTAX  SEQUENCE OF POLICYVLANBINDENTRY
            MAX-ACCESS  not-accessible
            STATUS  current
            DESCRIPTION
                    "A list of policy vlan binding entries.
                     Here you can bind a policy to a VLAN."
            ::= { policyBindConfigure 2 }

        polilyVlanBindEntry OBJECT-TYPE
            SYNTAX  POLICYVLANBINDENTRY
            MAX-ACCESS  not-accessible
            STATUS  current
            DESCRIPTION
                    "An entry contains of the information of policy vlan binding."
            INDEX   { vlanBindPolicyName,vlan}
            ::= { polilyVlanBindTable 1 }
    
        POLICYVLANBINDENTRY ::=
            SEQUENCE {
								vlanBindPolicyName
										OCTET STRING (SIZE (1..255)), 
								vlan
										INTEGER,
								policyVlanBindStatus
										RowStatus
            }
            
        vlanBindPolicyName OBJECT-TYPE
            SYNTAX  OCTET STRING (SIZE (1..255))  
            MAX-ACCESS  read-only
            STATUS  current
            DESCRIPTION
                    "The name of the policy you want to bind.(the policy name must be existent)"
            ::= { polilyVlanBindEntry 1 }
        
        vlan OBJECT-TYPE
            SYNTAX  INTEGER
            MAX-ACCESS  read-only
            STATUS  current
            DESCRIPTION
                    "the vlan that the policy bind to, the vlan must be existent"
            ::= { polilyVlanBindEntry 2 }
      
       policyVlanBindStatus OBJECT-TYPE
            SYNTAX  RowStatus
            MAX-ACCESS  read-create
            STATUS  current
            DESCRIPTION
                   "the following two values are states:
                   these values may be read or written
                   active(1),
                   notInService(2),

                   the following value is a state:
                   this value may be read, but not written
                   notReady(3),

                   the following three values are
                   actions: these values may be written,
                   but are never read
                   createAndGo(4),
                   createAndWait(5),
                   destroy(6)"
            ::= { polilyVlanBindEntry 3 }      
               
END
