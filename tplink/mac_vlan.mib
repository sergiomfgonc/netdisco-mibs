-- Performance vlan config
-- modify history: not change
--    

TLSG3424-MAC-VLAN-MIB DEFINITIONS ::= BEGIN

          IMPORTS
              RowStatus       	 
  					FROM SNMPv2-TC
              OBJECT-TYPE,MODULE-IDENTITY
          	  	         	FROM SNMPv2-SMI
              macVlan	          
          	  	          	FROM  TLSG3424-VLAN-MIB;
          	  	          	
       			macVlanConfig MODULE-IDENTITY  
			    LAST-UPDATED    "200812160000Z"
			    ORGANIZATION    "TPLINK"
			    CONTACT-INFO		"www.tplink.com.cn"
			    DESCRIPTION
			             "Implementation of the macvlan is mandatory for the swtich."
			    REVISION        "200908030000Z"
			    DESCRIPTION
					"Initial version of this MIB module."
			    ::= { macVlan 1 }      	      
      	             
          
           macVlanTable OBJECT-TYPE
              SYNTAX  SEQUENCE OF MACENTRY
              MAX-ACCESS  not-accessible
              STATUS  current
              DESCRIPTION
                      "MAC VLAN (Virtual Local Area Network) is the way to classify the 
                      VLANs based on MAC Address. A MAC address is relative to a single 
                      VLAN ID. The untagged packets and the priority-tagged packets coming 
                      from the MAC address will be tagged with this VLAN ID."
              ::= { macVlanConfig 1 }

          macVlanEntry OBJECT-TYPE
              SYNTAX  MACENTRY
              MAX-ACCESS  not-accessible
              STATUS  current
              DESCRIPTION
                      "An entry contains of the information of a mac vlan."
              INDEX   { macAddr }
              ::= { macVlanTable 1 }
      
          MACENTRY ::=
              SEQUENCE {
                  macAddr
                      OCTET STRING (SIZE (0..255)), 
                  macDescription
                      OCTET STRING (SIZE (0..255)), 
                  macVlanId
                 		 INTEGER,
                  macVlanStatus
                      RowStatus
              }
              
          macAddr OBJECT-TYPE
              SYNTAX  OCTET STRING (SIZE (0..255))  
              MAX-ACCESS  read-create
              STATUS  current
              DESCRIPTION
                      "Enter the MAC address."
              ::= { macVlanEntry 1 }
          
          macDescription OBJECT-TYPE
              SYNTAX  OCTET STRING (SIZE (0..255))  
              MAX-ACCESS  read-create
              STATUS  current
              DESCRIPTION
                      "Give a description to the MAC address for identification,
                      1-8 characters."
              ::= { macVlanEntry 2 }
              
          macVlanId OBJECT-TYPE
              SYNTAX  INTEGER (1..4094)
              MAX-ACCESS  read-create
              STATUS  current
              DESCRIPTION
                      "Enter the ID number of the MAC VLAN. This VLAN should be 
                      one of the 802.1Q VLANs the ingress port belongs to, 1-4094"
              ::= { macVlanEntry 3 }
             
       
            
         macVlanStatus OBJECT-TYPE
              SYNTAX  RowStatus
              MAX-ACCESS  read-create
              STATUS  current
              DESCRIPTION
                      "the following two values are states:
                     these values may be read or written
                     active(1),
                     notInService(2),

                     the following value is a state:
                     this value may be read, but not written
                     notReady(3),

                     the following three values are
                     actions: these values may be written,
                     but are never read
                     createAndGo(4),
                     createAndWait(5),
                     destroy(6)"
              ::= { macVlanEntry 4 }
              
          
      	
          END
